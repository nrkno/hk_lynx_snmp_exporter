-- Machine generated MIB file, do not edit!
--
-- MIB file for RCT5023-G, type code C2.08, software label 734
-- Generated on Tuesday, 09-Aug-16 16:26:46 UTC
-- CVS $Id: RCT5023-G_c208_sw734.mib,v 1.2 2016/08/09 16:26:47 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

RCT5023-G-c208-sw734-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

rct5023-g-c208-sw734 MODULE-IDENTITY
    LAST-UPDATED "201608091626Z"
    ORGANIZATION "LYNX Technik AG"
    CONTACT-INFO "LYNX Technik AG
        Brunnenweg 3
        64331 Weiterstadt
        http://www.lynx-technik.com
        mailto:support@lynx-technik.com"
    DESCRIPTION "MIB module definition for RCT5023-G, type code C2.08, software label 734"
    REVISION "201608091626Z"
    DESCRIPTION "Generated by LYNX Asset Database"
    ::= { mib-modules 49672734 }

rct5023-g-c208 OBJECT-IDENTITY
    STATUS current
    DESCRIPTION "LYNX device type RCT5023-G"
    ::= { products 49672 }

sw734 OBJECT-IDENTITY
    STATUS current
    DESCRIPTION "Software label 734"
    ::= { rct5023-g-c208 734 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeRackType ::= TEXTUAL-CONVENTION
    STATUS current
    DESCRIPTION "Enumeration"
    SYNTAX INTEGER {
        series3000(0),
        series5000(1)
    }

TypeFan1Status ::= TEXTUAL-CONVENTION
    STATUS current
    DESCRIPTION "Enumeration"
    SYNTAX INTEGER {
        ok(0),
        fail(1),
        missing(2)
    }

TypeAlarmTemp ::= TEXTUAL-CONVENTION
    STATUS current
    DESCRIPTION "Enumeration"
    SYNTAX INTEGER {
        none(0),
        minor(1),
        major(2)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

rackType OBJECT-TYPE
    SYNTAX TypeRackType
    MAX-ACCESS read-only
    STATUS current
    DESCRIPTION "Type of rack that this controller board is running in (Series 3000/5000)"
    ::= { paramEntry 14 }

gPO1Status OBJECT-TYPE
    SYNTAX OnOffValue
    MAX-ACCESS read-only
    STATUS current
    DESCRIPTION "Status of the GPO (General Purpose Output) contact 1 on the back of the rack (Minor Alarm)"
    ::= { paramEntry 15 }

gPO2Status OBJECT-TYPE
    SYNTAX OnOffValue
    MAX-ACCESS read-only
    STATUS current
    DESCRIPTION "Status of the GPO (General Purpose Output) contact 2 on the back of the rack (Major Alarm)"
    ::= { paramEntry 16 }

gPIStatus OBJECT-TYPE
    SYNTAX OnOffValue
    MAX-ACCESS read-only
    STATUS current
    DESCRIPTION "Status of the GPI (General Purpose Input) contact on the back of the Rack (on/off)"
    ::= { paramEntry 17 }

pSU1TypeAndVersion OBJECT-TYPE
    SYNTAX DisplayString
    MAX-ACCESS read-only
    STATUS current
    DESCRIPTION "Type name of power supply unit"
    ::= { paramEntry 18 }

pSU1Status OBJECT-TYPE
    SYNTAX DisplayString
    MAX-ACCESS read-only
    STATUS current
    DESCRIPTION "Status of power supply unit"
    ::= { paramEntry 19 }

pSU1Voltage OBJECT-TYPE
    SYNTAX FixedPointValue1
    MAX-ACCESS read-only
    STATUS current
    DESCRIPTION "Voltage of power supply unit"
    ::= { paramEntry 20 }

pSU1Temperature OBJECT-TYPE
    SYNTAX Integer32
    MAX-ACCESS read-only
    STATUS current
    DESCRIPTION "Temperature of power supply unit"
    ::= { paramEntry 21 }

pSU2TypeAndVersion OBJECT-TYPE
    SYNTAX DisplayString
    MAX-ACCESS read-only
    STATUS current
    DESCRIPTION "Type name of power supply unit"
    ::= { paramEntry 22 }

pSU2Status OBJECT-TYPE
    SYNTAX DisplayString
    MAX-ACCESS read-only
    STATUS current
    DESCRIPTION "Status of power supply unit"
    ::= { paramEntry 23 }

pSU2Voltage OBJECT-TYPE
    SYNTAX FixedPointValue1
    MAX-ACCESS read-only
    STATUS current
    DESCRIPTION "Voltage of power supply unit"
    ::= { paramEntry 24 }

pSU2Temperature OBJECT-TYPE
    SYNTAX Integer32
    MAX-ACCESS read-only
    STATUS current
    DESCRIPTION "Temperature of power supply unit"
    ::= { paramEntry 25 }

slotStatus1 OBJECT-TYPE
    SYNTAX DisplayString
    MAX-ACCESS read-only
    STATUS current
    DESCRIPTION "Slot Status 1: if present: set to name-and-version as in <name> VVV.VV.VV"
    ::= { paramEntry 26 }

slotStatus2 OBJECT-TYPE
    SYNTAX DisplayString
    MAX-ACCESS read-only
    STATUS current
    DESCRIPTION "Slot Status 2: if present: set to name-and-version as in <name> VVV.VV.VV"
    ::= { paramEntry 27 }

slotStatus3 OBJECT-TYPE
    SYNTAX DisplayString
    MAX-ACCESS read-only
    STATUS current
    DESCRIPTION "Slot Status 3: if present: set to name-and-version as in <name> VVV.VV.VV"
    ::= { paramEntry 28 }

slotStatus4 OBJECT-TYPE
    SYNTAX DisplayString
    MAX-ACCESS read-only
    STATUS current
    DESCRIPTION "Slot Status 4: if present: set to name-and-version as in <name> VVV.VV.VV"
    ::= { paramEntry 29 }

slotStatus5 OBJECT-TYPE
    SYNTAX DisplayString
    MAX-ACCESS read-only
    STATUS current
    DESCRIPTION "Slot Status 5: if present: set to name-and-version as in <name> VVV.VV.VV"
    ::= { paramEntry 30 }

slotStatus6 OBJECT-TYPE
    SYNTAX DisplayString
    MAX-ACCESS read-only
    STATUS current
    DESCRIPTION "Slot Status 6: if present: set to name-and-version as in <name> VVV.VV.VV"
    ::= { paramEntry 31 }

slotStatus7 OBJECT-TYPE
    SYNTAX DisplayString
    MAX-ACCESS read-only
    STATUS current
    DESCRIPTION "Slot Status 7: if present: set to name-and-version as in <name> VVV.VV.VV"
    ::= { paramEntry 32 }

slotStatus8 OBJECT-TYPE
    SYNTAX DisplayString
    MAX-ACCESS read-only
    STATUS current
    DESCRIPTION "Slot Status 8: if present: set to name-and-version as in <name> VVV.VV.VV"
    ::= { paramEntry 33 }

slotStatus9 OBJECT-TYPE
    SYNTAX DisplayString
    MAX-ACCESS read-only
    STATUS current
    DESCRIPTION "Slot Status 9: if present: set to name-and-version as in <name> VVV.VV.VV"
    ::= { paramEntry 34 }

slotStatus10 OBJECT-TYPE
    SYNTAX DisplayString
    MAX-ACCESS read-only
    STATUS current
    DESCRIPTION "Slot Status 10: if present: set to name-and-version as in <name> VVV.VV.VV"
    ::= { paramEntry 35 }

slotStatusPSU1 OBJECT-TYPE
    SYNTAX DisplayString
    MAX-ACCESS read-only
    STATUS current
    DESCRIPTION "Status PSU 1: if present: set to name-and-version as in <name> VVV.VV.VV"
    ::= { paramEntry 36 }

slotStatusPSU2 OBJECT-TYPE
    SYNTAX DisplayString
    MAX-ACCESS read-only
    STATUS current
    DESCRIPTION "Status PSU 2: if present: set to name-and-version as in <name> VVV.VV.VV"
    ::= { paramEntry 37 }

slotStatusFan1 OBJECT-TYPE
    SYNTAX DisplayString
    MAX-ACCESS read-only
    STATUS current
    DESCRIPTION "Status Fan 1: if present: set to name-and-version as in <name> VVV.VV.VV"
    ::= { paramEntry 38 }

slotStatusFan2 OBJECT-TYPE
    SYNTAX DisplayString
    MAX-ACCESS read-only
    STATUS current
    DESCRIPTION "Status Fan 2: if present: set to name-and-version as in <name> VVV.VV.VV"
    ::= { paramEntry 39 }

slotStatusFan3 OBJECT-TYPE
    SYNTAX DisplayString
    MAX-ACCESS read-only
    STATUS current
    DESCRIPTION "Status Fan 3: if present: set to name-and-version as in <name> VVV.VV.VV"
    ::= { paramEntry 40 }

fan1Status OBJECT-TYPE
    SYNTAX TypeFan1Status
    MAX-ACCESS read-only
    STATUS current
    DESCRIPTION "Current status of fan 1"
    ::= { paramEntry 41 }

fan2Status OBJECT-TYPE
    SYNTAX TypeFan1Status
    MAX-ACCESS read-only
    STATUS current
    DESCRIPTION "Current status of fan 2"
    ::= { paramEntry 42 }

fan3Status OBJECT-TYPE
    SYNTAX TypeFan1Status
    MAX-ACCESS read-only
    STATUS current
    DESCRIPTION "Current status of fan 3"
    ::= { paramEntry 43 }

alarmTemp OBJECT-TYPE
    SYNTAX TypeAlarmTemp
    MAX-ACCESS read-write
    STATUS current
    DESCRIPTION "Specify whether a High Temperature event shall trigger a Major or Minor Alarm (GPO contact) or none of the above."
    ::= { paramEntry 44 }

alarmVolt OBJECT-TYPE
    SYNTAX TypeAlarmTemp
    MAX-ACCESS read-write
    STATUS current
    DESCRIPTION "Specify whether a Voltage out of range event shall trigger a Major or Minor Alarm (GPO contact) or none of the above."
    ::= { paramEntry 45 }

alarmRPS1 OBJECT-TYPE
    SYNTAX TypeAlarmTemp
    MAX-ACCESS read-write
    STATUS current
    DESCRIPTION "Specify whether a One RPS missing event shall trigger a Major or Minor Alarm (GPO contact) or none of the above."
    ::= { paramEntry 46 }

alarmFanFail OBJECT-TYPE
    SYNTAX TypeAlarmTemp
    MAX-ACCESS read-write
    STATUS current
    DESCRIPTION "Specify whether a Fan Failure event shall trigger a Major or Minor Alarm (GPO contact) or none of the above."
    ::= { paramEntry 47 }

alarmFanLost OBJECT-TYPE
    SYNTAX TypeAlarmTemp
    MAX-ACCESS read-write
    STATUS current
    DESCRIPTION "Specify whether a Front Panel Fan missing event shall trigger a Major or Minor Alarm (GPO contact) or none of the above."
    ::= { paramEntry 48 }

hotsync OBJECT-TYPE
    SYNTAX OnOffValue
    MAX-ACCESS read-write
    STATUS current
    DESCRIPTION "HotSync adds data security as a reliable and automatic recovery mechanism for configuration data of individual processing devices.<br>HotSync is enabled as a function of a RackController and applies to all devices in the controllers stack, i.e. in the local RackFrame and in connected Extensions, if any.<br>When enabled, HotSync automatically maintains a dynamic copy of the current configuration for all devices. The backup copy is stored inside the controller. You can think of this mechanism as if a backup copy of the device-settings were <i>stored in the slot</i>.<br>If you ever have to replace a processing board, and you bring a new device of the same type into the same slot, then HotSync will automatically copy the last valid settings from the controllers backup-memory into the new board"
    ::= { paramEntry 49 }

sNumber OBJECT-TYPE
    SYNTAX DisplayString
    MAX-ACCESS read-only
    STATUS current
    DESCRIPTION "Serial Number"
    ::= { paramEntry 73 }

-- Parameter table
paramTable OBJECT-TYPE
    SYNTAX SEQUENCE OF ParamEntry
    MAX-ACCESS not-accessible
    STATUS current
    DESCRIPTION "Table of RCT5023-G parameters"
    ::= { sw734 1 }

paramEntry OBJECT-TYPE
    SYNTAX ParamEntry
    MAX-ACCESS not-accessible
    STATUS current
    DESCRIPTION "A row in the table of RCT5023-G parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    rackType TypeRackType,
    gPO1Status OnOffValue,
    gPO2Status OnOffValue,
    gPIStatus OnOffValue,
    pSU1TypeAndVersion DisplayString,
    pSU1Status DisplayString,
    pSU1Voltage FixedPointValue1,
    pSU1Temperature Integer32,
    pSU2TypeAndVersion DisplayString,
    pSU2Status DisplayString,
    pSU2Voltage FixedPointValue1,
    pSU2Temperature Integer32,
    slotStatus1 DisplayString,
    slotStatus2 DisplayString,
    slotStatus3 DisplayString,
    slotStatus4 DisplayString,
    slotStatus5 DisplayString,
    slotStatus6 DisplayString,
    slotStatus7 DisplayString,
    slotStatus8 DisplayString,
    slotStatus9 DisplayString,
    slotStatus10 DisplayString,
    slotStatusPSU1 DisplayString,
    slotStatusPSU2 DisplayString,
    slotStatusFan1 DisplayString,
    slotStatusFan2 DisplayString,
    slotStatusFan3 DisplayString,
    fan1Status TypeFan1Status,
    fan2Status TypeFan1Status,
    fan3Status TypeFan1Status,
    alarmTemp TypeAlarmTemp,
    alarmVolt TypeAlarmTemp,
    alarmRPS1 TypeAlarmTemp,
    alarmFanFail TypeAlarmTemp,
    alarmFanLost TypeAlarmTemp,
    hotsync OnOffValue,
    sNumber DisplayString }

-- Conformance statements
conformance OBJECT-IDENTITY
    STATUS current
    DESCRIPTION "Conformance declaration of RCT5023-G"
    ::= { sw734 2 }

paramGroup OBJECT-GROUP
    OBJECTS {
        typeName,
        displayName,
        position,
        uptime,
        type,
        version,
        statusColor,
        statusColorRGB,
        statusText,
        factoryReset,
        lock,
        locate,
        rackType,
        gPO1Status,
        gPO2Status,
        gPIStatus,
        pSU1TypeAndVersion,
        pSU1Status,
        pSU1Voltage,
        pSU1Temperature,
        pSU2TypeAndVersion,
        pSU2Status,
        pSU2Voltage,
        pSU2Temperature,
        slotStatus1,
        slotStatus2,
        slotStatus3,
        slotStatus4,
        slotStatus5,
        slotStatus6,
        slotStatus7,
        slotStatus8,
        slotStatus9,
        slotStatus10,
        slotStatusPSU1,
        slotStatusPSU2,
        slotStatusFan1,
        slotStatusFan2,
        slotStatusFan3,
        fan1Status,
        fan2Status,
        fan3Status,
        alarmTemp,
        alarmVolt,
        alarmRPS1,
        alarmFanFail,
        alarmFanLost,
        hotsync,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
