-- Machine generated MIB file, do not edit!
--
-- MIB file for OTX5840, type code 08.DB, software label 619
-- Generated on Tuesday, 09-Aug-16 14:43:57 UTC
-- CVS $Id: OTX5840_08db_sw619.mib,v 1.4 2016/08/09 14:43:59 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

OTX5840-08db-sw619-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

otx5840-08db-sw619 MODULE-IDENTITY
    LAST-UPDATED "201608091443Z"
    ORGANIZATION "LYNX Technik AG"
    CONTACT-INFO "LYNX Technik AG
        Brunnenweg 3
        64331 Weiterstadt
        http://www.lynx-technik.com
        mailto:support@lynx-technik.com"
    DESCRIPTION "MIB module definition for OTX5840, type code 08.DB, software label 619"
    REVISION "201608091443Z"
    DESCRIPTION "Generated by LYNX Asset Database"
    ::= { mib-modules 2267619 }

otx5840-08db OBJECT-IDENTITY
    STATUS current
    DESCRIPTION "LYNX device type OTX5840"
    ::= { products 2267 }

sw619 OBJECT-IDENTITY
    STATUS current
    DESCRIPTION "Software label 619"
    ::= { otx5840-08db 619 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeIn1 ::= TEXTUAL-CONVENTION
    STATUS current
    DESCRIPTION "Enumeration"
    SYNTAX INTEGER {
        missing(0),
        sDSDI(1),
        hDSDI(2),
        n3GSDI(3),
        hD3G(4),
        present(5)
    }

TypeSignalType ::= TEXTUAL-CONVENTION
    STATUS current
    DESCRIPTION "Enumeration"
    SYNTAX INTEGER {
        slow(0),
        fast(1)
    }

TypeSourceOut1 ::= TEXTUAL-CONVENTION
    STATUS current
    DESCRIPTION "Enumeration"
    SYNTAX INTEGER {
        in1(0),
        in2(1),
        in3(2),
        in4(3)
    }

TypeEventPrimaryPowermissingSNMP ::= TEXTUAL-CONVENTION
    STATUS current
    DESCRIPTION "Enumeration"
    SYNTAX INTEGER {
        none(0),
        onOnly(1),
        offOnly(2),
        onOff(3)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

boardID OBJECT-TYPE
    SYNTAX Integer32
    MAX-ACCESS read-only
    STATUS current
    DESCRIPTION "BoardID"
    ::= { paramEntry 13 }

eventSDIInput1NoInput OBJECT-TYPE
    SYNTAX OnOffValue
    MAX-ACCESS read-only
    STATUS current
    DESCRIPTION "SDI Input 1: No Input"
    ::= { paramEntry 15 }

eventSDIInput2NoInput OBJECT-TYPE
    SYNTAX OnOffValue
    MAX-ACCESS read-only
    STATUS current
    DESCRIPTION "SDI Input 2: No Input"
    ::= { paramEntry 16 }

eventSDIInput3NoInput OBJECT-TYPE
    SYNTAX OnOffValue
    MAX-ACCESS read-only
    STATUS current
    DESCRIPTION "SDI Input 3: No Input"
    ::= { paramEntry 17 }

eventSDIInput4NoInput OBJECT-TYPE
    SYNTAX OnOffValue
    MAX-ACCESS read-only
    STATUS current
    DESCRIPTION "SDI Input 4: No Input"
    ::= { paramEntry 18 }

eventPrimaryPowermissing OBJECT-TYPE
    SYNTAX OnOffValue
    MAX-ACCESS read-only
    STATUS current
    DESCRIPTION "Info Event: Primary Power missing"
    ::= { paramEntry 19 }

eventRedundantPowermissing OBJECT-TYPE
    SYNTAX OnOffValue
    MAX-ACCESS read-only
    STATUS current
    DESCRIPTION "Info Event: Redundant Power missing"
    ::= { paramEntry 20 }

in1 OBJECT-TYPE
    SYNTAX TypeIn1
    MAX-ACCESS read-only
    STATUS current
    DESCRIPTION "Input status channel 1"
    ::= { paramEntry 21 }

in2 OBJECT-TYPE
    SYNTAX TypeIn1
    MAX-ACCESS read-only
    STATUS current
    DESCRIPTION "Input status channel 2"
    ::= { paramEntry 22 }

in3 OBJECT-TYPE
    SYNTAX TypeIn1
    MAX-ACCESS read-only
    STATUS current
    DESCRIPTION "Input status channel 3"
    ::= { paramEntry 23 }

in4 OBJECT-TYPE
    SYNTAX TypeIn1
    MAX-ACCESS read-only
    STATUS current
    DESCRIPTION "Input status channel 4"
    ::= { paramEntry 24 }

out1 OBJECT-TYPE
    SYNTAX TypeIn1
    MAX-ACCESS read-only
    STATUS current
    DESCRIPTION "Output status channel 1"
    ::= { paramEntry 25 }

out2 OBJECT-TYPE
    SYNTAX TypeIn1
    MAX-ACCESS read-only
    STATUS current
    DESCRIPTION "Output status channel 2"
    ::= { paramEntry 26 }

out3 OBJECT-TYPE
    SYNTAX TypeIn1
    MAX-ACCESS read-only
    STATUS current
    DESCRIPTION "Output status channel 3"
    ::= { paramEntry 27 }

out4 OBJECT-TYPE
    SYNTAX TypeIn1
    MAX-ACCESS read-only
    STATUS current
    DESCRIPTION "Output status channel 4"
    ::= { paramEntry 28 }

out5 OBJECT-TYPE
    SYNTAX TypeIn1
    MAX-ACCESS read-only
    STATUS current
    DESCRIPTION "Output status channel 5"
    ::= { paramEntry 29 }

out6 OBJECT-TYPE
    SYNTAX TypeIn1
    MAX-ACCESS read-only
    STATUS current
    DESCRIPTION "Output status channel 6"
    ::= { paramEntry 30 }

signalType OBJECT-TYPE
    SYNTAX TypeSignalType
    MAX-ACCESS read-write
    STATUS current
    DESCRIPTION "This switch configures the slew rate (rise/fall time) of all output signals that are connected to such input(s) where the reclocker is manually switched off.
In this case (reclocker off), the signal speed cannot be detected automatically and therefore the output configuration has to be set manually with this switch."
    ::= { paramEntry 31 }

reclock1 OBJECT-TYPE
    SYNTAX OnOffValue
    MAX-ACCESS read-write
    STATUS current
    DESCRIPTION "select SDI reclocking on input 1"
    ::= { paramEntry 32 }

reclock2 OBJECT-TYPE
    SYNTAX OnOffValue
    MAX-ACCESS read-write
    STATUS current
    DESCRIPTION "select SDI reclocking on input 2"
    ::= { paramEntry 33 }

reclock3 OBJECT-TYPE
    SYNTAX OnOffValue
    MAX-ACCESS read-write
    STATUS current
    DESCRIPTION "select SDI reclocking on input 3"
    ::= { paramEntry 34 }

reclock4 OBJECT-TYPE
    SYNTAX OnOffValue
    MAX-ACCESS read-write
    STATUS current
    DESCRIPTION "select SDI reclocking on input 4"
    ::= { paramEntry 35 }

sFPModuleType1 OBJECT-TYPE
    SYNTAX DisplayString
    MAX-ACCESS read-only
    STATUS current
    DESCRIPTION "displays the type of detected SFP-Module 1. The SFP part number will also be  displayed if SFP-Module is unknown."
    ::= { paramEntry 36 }

sFPModulePartNumber1 OBJECT-TYPE
    SYNTAX DisplayString
    MAX-ACCESS read-only
    STATUS current
    DESCRIPTION "Displays the part number of used SFP Module"
    ::= { paramEntry 37 }

sFPModuleType2 OBJECT-TYPE
    SYNTAX DisplayString
    MAX-ACCESS read-only
    STATUS current
    DESCRIPTION "displays the type of detected SFP-Module 2. The SFP part number will also be  displayed if SFP-Module is unknown."
    ::= { paramEntry 38 }

sFPModulePartNumber2 OBJECT-TYPE
    SYNTAX DisplayString
    MAX-ACCESS read-only
    STATUS current
    DESCRIPTION "Displays the part number of used SFP Module"
    ::= { paramEntry 39 }

sourceOut1 OBJECT-TYPE
    SYNTAX TypeSourceOut1
    MAX-ACCESS read-write
    STATUS current
    DESCRIPTION "Select Source stream for output 1 from input 1 or 2"
    ::= { paramEntry 40 }

sourceOut2 OBJECT-TYPE
    SYNTAX TypeSourceOut1
    MAX-ACCESS read-write
    STATUS current
    DESCRIPTION "Select Source stream for output 2 from input 1 or 2"
    ::= { paramEntry 41 }

sourceOut3 OBJECT-TYPE
    SYNTAX TypeSourceOut1
    MAX-ACCESS read-write
    STATUS current
    DESCRIPTION "Select Source stream for output 3 from input 1 or 2"
    ::= { paramEntry 42 }

sourceOut4 OBJECT-TYPE
    SYNTAX TypeSourceOut1
    MAX-ACCESS read-write
    STATUS current
    DESCRIPTION "Select Source stream for output 4 from input 1 or 2"
    ::= { paramEntry 43 }

sourceOut5 OBJECT-TYPE
    SYNTAX TypeSourceOut1
    MAX-ACCESS read-write
    STATUS current
    DESCRIPTION "Select Source stream for output 5 from input 1 or 2"
    ::= { paramEntry 44 }

sourceOut6 OBJECT-TYPE
    SYNTAX TypeSourceOut1
    MAX-ACCESS read-write
    STATUS current
    DESCRIPTION "Select Source stream for output 6 from input 1 or 2"
    ::= { paramEntry 45 }

autoDisableOpticalOutput OBJECT-TYPE
    SYNTAX OnOffValue
    MAX-ACCESS read-write
    STATUS current
    DESCRIPTION "automatically disable (power down) the laser transmitter of the optical output if no valid input signal is connected."
    ::= { paramEntry 46 }

eventVideoInput1NoInput OBJECT-TYPE
    SYNTAX OnOffValue
    MAX-ACCESS read-only
    STATUS current
    DESCRIPTION "Warning Event: Video Input 1 No Input"
    ::= { paramEntry 47 }

eventVideoInput2NoInput OBJECT-TYPE
    SYNTAX OnOffValue
    MAX-ACCESS read-only
    STATUS current
    DESCRIPTION "Warning Event: Video Input 2 No Input"
    ::= { paramEntry 48 }

eventVideoInput3NoInput OBJECT-TYPE
    SYNTAX OnOffValue
    MAX-ACCESS read-only
    STATUS current
    DESCRIPTION "Warning Event: Video Input 3 No Input"
    ::= { paramEntry 49 }

eventVideoInput4NoInput OBJECT-TYPE
    SYNTAX OnOffValue
    MAX-ACCESS read-only
    STATUS current
    DESCRIPTION "Warning Event: Video Input 4 No Input"
    ::= { paramEntry 50 }

eventPrimaryPowermissingSNMP OBJECT-TYPE
    SYNTAX TypeEventPrimaryPowermissingSNMP
    MAX-ACCESS read-write
    STATUS current
    DESCRIPTION "SNMP Trap for  Event: Primary Power missing"
    ::= { paramEntry 51 }

eventRedundantPowermissingSNMP OBJECT-TYPE
    SYNTAX TypeEventPrimaryPowermissingSNMP
    MAX-ACCESS read-write
    STATUS current
    DESCRIPTION "SNMP Trap for  Event: Redundant Power missing"
    ::= { paramEntry 52 }

eventVideoInput1NoInputSNMP OBJECT-TYPE
    SYNTAX TypeEventPrimaryPowermissingSNMP
    MAX-ACCESS read-write
    STATUS current
    DESCRIPTION "SNMP Trap for  Event: Video Input 1 No Input"
    ::= { paramEntry 53 }

eventVideoInput2NoInputSNMP OBJECT-TYPE
    SYNTAX TypeEventPrimaryPowermissingSNMP
    MAX-ACCESS read-write
    STATUS current
    DESCRIPTION "SNMP Trap for  Event: Video Input 2 No Input"
    ::= { paramEntry 54 }

eventVideoInput3NoInputSNMP OBJECT-TYPE
    SYNTAX TypeEventPrimaryPowermissingSNMP
    MAX-ACCESS read-write
    STATUS current
    DESCRIPTION "SNMP Trap for  Event: Video Input 3 No Input"
    ::= { paramEntry 55 }

eventVideoInput4NoInputSNMP OBJECT-TYPE
    SYNTAX TypeEventPrimaryPowermissingSNMP
    MAX-ACCESS read-write
    STATUS current
    DESCRIPTION "SNMP Trap for  Event: Video Input 4 No Input"
    ::= { paramEntry 56 }

sFP1OutPower OBJECT-TYPE
    SYNTAX DisplayString
    MAX-ACCESS read-only
    STATUS current
    DESCRIPTION "displays the average output power of detected SFP-Module 1."
    ::= { paramEntry 57 }

sFP1Wavelength1 OBJECT-TYPE
    SYNTAX DisplayString
    MAX-ACCESS read-only
    STATUS current
    DESCRIPTION "displays the wavelength of detected SFP-Module 1."
    ::= { paramEntry 58 }

sFP1Wavelength2 OBJECT-TYPE
    SYNTAX DisplayString
    MAX-ACCESS read-only
    STATUS current
    DESCRIPTION "displays the wavelength of detected SFP-Module 1."
    ::= { paramEntry 59 }

sFP2OutPower OBJECT-TYPE
    SYNTAX DisplayString
    MAX-ACCESS read-only
    STATUS current
    DESCRIPTION "displays the average output power of detected SFP-Module 2."
    ::= { paramEntry 60 }

sFP2Wavelength1 OBJECT-TYPE
    SYNTAX DisplayString
    MAX-ACCESS read-only
    STATUS current
    DESCRIPTION "displays the wavelength of detected SFP-Module 2."
    ::= { paramEntry 61 }

sFP2Wavelength2 OBJECT-TYPE
    SYNTAX DisplayString
    MAX-ACCESS read-only
    STATUS current
    DESCRIPTION "displays the wavelength of detected SFP-Module 2."
    ::= { paramEntry 62 }

sNumber OBJECT-TYPE
    SYNTAX DisplayString
    MAX-ACCESS read-only
    STATUS current
    DESCRIPTION "Serial Number"
    ::= { paramEntry 63 }

-- Parameter table
paramTable OBJECT-TYPE
    SYNTAX SEQUENCE OF ParamEntry
    MAX-ACCESS not-accessible
    STATUS current
    DESCRIPTION "Table of OTX5840 parameters"
    ::= { sw619 1 }

paramEntry OBJECT-TYPE
    SYNTAX ParamEntry
    MAX-ACCESS not-accessible
    STATUS current
    DESCRIPTION "A row in the table of OTX5840 parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    boardID Integer32,
    eventSDIInput1NoInput OnOffValue,
    eventSDIInput2NoInput OnOffValue,
    eventSDIInput3NoInput OnOffValue,
    eventSDIInput4NoInput OnOffValue,
    eventPrimaryPowermissing OnOffValue,
    eventRedundantPowermissing OnOffValue,
    in1 TypeIn1,
    in2 TypeIn1,
    in3 TypeIn1,
    in4 TypeIn1,
    out1 TypeIn1,
    out2 TypeIn1,
    out3 TypeIn1,
    out4 TypeIn1,
    out5 TypeIn1,
    out6 TypeIn1,
    signalType TypeSignalType,
    reclock1 OnOffValue,
    reclock2 OnOffValue,
    reclock3 OnOffValue,
    reclock4 OnOffValue,
    sFPModuleType1 DisplayString,
    sFPModulePartNumber1 DisplayString,
    sFPModuleType2 DisplayString,
    sFPModulePartNumber2 DisplayString,
    sourceOut1 TypeSourceOut1,
    sourceOut2 TypeSourceOut1,
    sourceOut3 TypeSourceOut1,
    sourceOut4 TypeSourceOut1,
    sourceOut5 TypeSourceOut1,
    sourceOut6 TypeSourceOut1,
    autoDisableOpticalOutput OnOffValue,
    eventVideoInput1NoInput OnOffValue,
    eventVideoInput2NoInput OnOffValue,
    eventVideoInput3NoInput OnOffValue,
    eventVideoInput4NoInput OnOffValue,
    eventPrimaryPowermissingSNMP TypeEventPrimaryPowermissingSNMP,
    eventRedundantPowermissingSNMP TypeEventPrimaryPowermissingSNMP,
    eventVideoInput1NoInputSNMP TypeEventPrimaryPowermissingSNMP,
    eventVideoInput2NoInputSNMP TypeEventPrimaryPowermissingSNMP,
    eventVideoInput3NoInputSNMP TypeEventPrimaryPowermissingSNMP,
    eventVideoInput4NoInputSNMP TypeEventPrimaryPowermissingSNMP,
    sFP1OutPower DisplayString,
    sFP1Wavelength1 DisplayString,
    sFP1Wavelength2 DisplayString,
    sFP2OutPower DisplayString,
    sFP2Wavelength1 DisplayString,
    sFP2Wavelength2 DisplayString,
    sNumber DisplayString }

-- Conformance statements
conformance OBJECT-IDENTITY
    STATUS current
    DESCRIPTION "Conformance declaration of OTX5840"
    ::= { sw619 2 }

paramGroup OBJECT-GROUP
    OBJECTS {
        typeName,
        displayName,
        position,
        uptime,
        type,
        version,
        statusColor,
        statusColorRGB,
        statusText,
        factoryReset,
        lock,
        locate,
        boardID,
        eventSDIInput1NoInput,
        eventSDIInput2NoInput,
        eventSDIInput3NoInput,
        eventSDIInput4NoInput,
        eventPrimaryPowermissing,
        eventRedundantPowermissing,
        in1,
        in2,
        in3,
        in4,
        out1,
        out2,
        out3,
        out4,
        out5,
        out6,
        signalType,
        reclock1,
        reclock2,
        reclock3,
        reclock4,
        sFPModuleType1,
        sFPModulePartNumber1,
        sFPModuleType2,
        sFPModulePartNumber2,
        sourceOut1,
        sourceOut2,
        sourceOut3,
        sourceOut4,
        sourceOut5,
        sourceOut6,
        autoDisableOpticalOutput,
        eventVideoInput1NoInput,
        eventVideoInput2NoInput,
        eventVideoInput3NoInput,
        eventVideoInput4NoInput,
        eventPrimaryPowermissingSNMP,
        eventRedundantPowermissingSNMP,
        eventVideoInput1NoInputSNMP,
        eventVideoInput2NoInputSNMP,
        eventVideoInput3NoInputSNMP,
        eventVideoInput4NoInputSNMP,
        sFP1OutPower,
        sFP1Wavelength1,
        sFP1Wavelength2,
        sFP2OutPower,
        sFP2Wavelength1,
        sFP2Wavelength2,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
