-- Machine generated MIB file, do not edit!
--
-- MIB file for PVD5800-O, type code 07.F1, software label 762
-- Generated on Monday, 24-Oct-16 15:48:59 UTC
-- CVS $Id: PVD5800-O_07f1_sw762.mib,v 1.1 2016/10/24 15:49:00 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

PVD5800-O-07f1-sw762-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

pvd5800-o-07f1-sw762 MODULE-IDENTITY
    LAST-UPDATED "201610241548Z"
    ORGANIZATION "LYNX Technik AG"
    CONTACT-INFO "LYNX Technik AG
        Brunnenweg 3
        64331 Weiterstadt
        http://www.lynx-technik.com
        mailto:support@lynx-technik.com"
    DESCRIPTION "MIB module definition for PVD5800-O, type code 07.F1, software label 762"
    REVISION "201610241548Z"
    DESCRIPTION "Generated by LYNX Asset Database"
    ::= { mib-modules 2033762 }

pvd5800-o-07f1 OBJECT-IDENTITY
    STATUS current
    DESCRIPTION "LYNX device type PVD5800-O"
    ::= { products 2033 }

sw762 OBJECT-IDENTITY
    STATUS current
    DESCRIPTION "Software label 762"
    ::= { pvd5800-o-07f1 762 }

-- Type definitions
TypeFactoryReset ::= TEXTUAL-CONVENTION
    STATUS current
    DESCRIPTION "Enumeration"
    SYNTAX INTEGER {
        press(0)
    }

TypeBackpanelStatus ::= TEXTUAL-CONVENTION
    STATUS current
    DESCRIPTION "Enumeration"
    SYNTAX INTEGER {
        nA(0),
        missing(1),
        present(2)
    }

TypeOutStandard ::= TEXTUAL-CONVENTION
    STATUS current
    DESCRIPTION "Enumeration"
    SYNTAX INTEGER {
        missing(0),
        invalid(1),
        n525(2),
        n625(3),
        n720p60(4),
        n720p5994(5),
        n720p50(6),
        n720p30(7),
        n720p2997(8),
        n720p25(9),
        n720p24(10),
        n720p2398(11),
        n1080i60(12),
        n1080i5994(13),
        n1080i50(14),
        n1080p60(15),
        n1080p5994(16),
        n1080p50(17),
        n1080p30(18),
        n1080p2997(19),
        n1080p25(20),
        n1080p24(21),
        n1080p2398(22),
        n1080psF30(23),
        n1080psF2997(24),
        n1080psF25(25),
        n1080psF24(26),
        n1080psF2398(27)
    }

TypeDelayVideoUserMode ::= TEXTUAL-CONVENTION
    STATUS current
    DESCRIPTION "Enumeration"
    SYNTAX INTEGER {
        framesLinesPixels(0),
        milliseconds(1)
    }

TypeReferenceLock ::= TEXTUAL-CONVENTION
    STATUS current
    DESCRIPTION "Enumeration"
    SYNTAX INTEGER {
        lockToRefIn(0),
        lockToSDI1(1)
    }

TypeReferenceSource ::= TEXTUAL-CONVENTION
    STATUS current
    DESCRIPTION "Enumeration"
    SYNTAX INTEGER {
        externBoard(0),
        internRack(1)
    }

TypeFreqPreselect ::= TEXTUAL-CONVENTION
    STATUS current
    DESCRIPTION "Enumeration"
    SYNTAX INTEGER {
        evenFrequencies(0),
        oddFrequencies(1),
        followLastRefInput(2)
    }

TypeFreq ::= TEXTUAL-CONVENTION
    STATUS current
    DESCRIPTION "Enumeration"
    SYNTAX INTEGER {
        evenFreq(0),
        oddFreq(1),
        evenFreqX(2),
        oddFreqX(3),
        evenFreqXX(4)
    }

TypeGPIFunc ::= TEXTUAL-CONVENTION
    STATUS current
    DESCRIPTION "Enumeration"
    SYNTAX INTEGER {
        none(0),
        freezeInput1(1),
        freezeInput2(2),
        freezeBothInputs(3),
        switchUserPresets(4)
    }

TypeSyncMode1 ::= TEXTUAL-CONVENTION
    STATUS current
    DESCRIPTION "Enumeration"
    SYNTAX INTEGER {
        frameSync(0),
        lineSyncH(1),
        lineSyncV(2)
    }

TypeInputFreezeSDI1 ::= TEXTUAL-CONVENTION
    STATUS current
    DESCRIPTION "Enumeration"
    SYNTAX INTEGER {
        freezeOnTRSError(0),
        transparentForTRSErrors(1),
        forceFreeze(2)
    }

TypeOut1TestPatternSelect ::= TEXTUAL-CONVENTION
    STATUS current
    DESCRIPTION "Enumeration"
    SYNTAX INTEGER {
        black(0),
        red(1),
        green(2),
        blue(3),
        cyan(4),
        magenta(5),
        yellow(6),
        white(7),
        n15Grey(8),
        eQPath(9),
        pLLPath(10),
        eQPLLPath(11),
        n75Colorbar(12),
        colorbarOverRed(13)
    }

TypeOut1TestPatternStd ::= TEXTUAL-CONVENTION
    STATUS current
    DESCRIPTION "Enumeration"
    SYNTAX INTEGER {
        n525(0),
        n625(1),
        n720p60(2),
        n720p5994(3),
        n720p50(4),
        n720p30(5),
        n720p2997(6),
        n720p25(7),
        n720p24(8),
        n720p2398(9),
        n1080i60(10),
        n1080i5994(11),
        n1080i50(12),
        n1080p30(13),
        n1080p2997(14),
        n1080p25(15),
        n1080p24(16),
        n1080p2398(17),
        n1080psF24(18),
        n1080psF2398(19),
        n1080p60(20),
        n1080p5994(21),
        n1080p50(22),
        n1080psF30(23),
        n1080psF2997(24),
        n1080psF25(25),
        followLastInput(26)
    }

TypeOut1IfNoInput ::= TEXTUAL-CONVENTION
    STATUS current
    DESCRIPTION "Enumeration"
    SYNTAX INTEGER {
        off(0),
        testPattern(1),
        black(2),
        freeze(3)
    }

TypeSDIIn1SourceType ::= TEXTUAL-CONVENTION
    STATUS current
    DESCRIPTION "Enumeration"
    SYNTAX INTEGER {
        electrical(0),
        optical(1)
    }

TypePresetsGPIOn ::= TEXTUAL-CONVENTION
    STATUS current
    DESCRIPTION "Enumeration"
    SYNTAX INTEGER {
        current(0),
        preset1(1),
        preset2(2),
        preset3(3),
        preset4(4),
        preset5(5),
        preset6(6),
        preset7(7)
    }

TypeOut1FreezeMode ::= TEXTUAL-CONVENTION
    STATUS current
    DESCRIPTION "Enumeration"
    SYNTAX INTEGER {
        freezeField1(0),
        freezeField2(1),
        freezeFrame(2),
        testPattern(3)
    }

TypeStatusColor ::= TEXTUAL-CONVENTION
    STATUS current
    DESCRIPTION "Enumeration"
    SYNTAX INTEGER {
        unknown(0),
        black(1),
        green(2),
        yellow(3),
        red(4)
    }

TypePresetsSaveAs ::= TEXTUAL-CONVENTION
    STATUS current
    DESCRIPTION "Enumeration"
    SYNTAX INTEGER {
        nA(0),
        preset1(1),
        preset2(2),
        preset3(3),
        preset4(4),
        preset5(5),
        preset6(6),
        preset7(7)
    }

TypePresetsCurrentSettingsBasedOn ::= TEXTUAL-CONVENTION
    STATUS current
    DESCRIPTION "Enumeration"
    SYNTAX INTEGER {
        default(0),
        preset1(1),
        preset2(2),
        preset3(3),
        preset4(4),
        preset5(5),
        preset6(6),
        preset7(7)
    }

TypeEventPrimaryPowermissingSNMP ::= TEXTUAL-CONVENTION
    STATUS current
    DESCRIPTION "Enumeration"
    SYNTAX INTEGER {
        none(0),
        onOnly(1),
        offOnly(2),
        onOff(3)
    }

TypeSDIIn13GFormat ::= TEXTUAL-CONVENTION
    STATUS current
    DESCRIPTION "Enumeration"
    SYNTAX INTEGER {
        nA(0),
        levelA(1),
        levelBDL2x(2),
        levelBDLGetOption(3),
        levelBDL444(4),
        levelBDLRGB(5),
        levelBDLRGB444(6),
        levelBDL12Bit(7),
        levelBDL44412Bit(8),
        levelBDLRGB12Bit(9),
        levelBDLRGB44412Bit(10),
        levelA444(11),
        levelARGB(12),
        levelARGB444(13),
        levelA12Bit(14),
        levelA44412Bit(15),
        levelARGB12Bit(16),
        levelARGB44412Bit(17),
        levelBDS(18)
    }

TypeSDIIn1DeembedFrom3GLevelB ::= TEXTUAL-CONVENTION
    STATUS current
    DESCRIPTION "Enumeration"
    SYNTAX INTEGER {
        streamA(0),
        streamB(1)
    }

TypeOut13GFormat ::= TEXTUAL-CONVENTION
    STATUS current
    DESCRIPTION "Enumeration"
    SYNTAX INTEGER {
        nA(0),
        levelA(1),
        levelBDL2x(2),
        levelBDL444(3),
        levelBDLRGB(4),
        levelBDLRGB444(5),
        levelBDL12Bit(6),
        levelBDL44412Bit(7),
        levelBDLRGB12Bit(8),
        levelBDLRGB44412Bit(9),
        levelBDS(10)
    }

TypeOut1SDI3GTransport ::= TEXTUAL-CONVENTION
    STATUS current
    DESCRIPTION "Enumeration"
    SYNTAX INTEGER {
        auto(0),
        levelA(1),
        levelBDualLink(2)
    }

TypeOut1Embed3GLevelBStreamSelect ::= TEXTUAL-CONVENTION
    STATUS current
    DESCRIPTION "Enumeration"
    SYNTAX INTEGER {
        streamAOnly(0),
        streamBOnly(1),
        streamsAB(2)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

factoryReset OBJECT-TYPE
    SYNTAX TypeFactoryReset
    MAX-ACCESS read-write
    STATUS current
    DESCRIPTION "Reset device to factory default values (set value to PRESS for execution)"
    ::= { paramEntry 7 }

lock OBJECT-TYPE
    SYNTAX OnOffValue
    MAX-ACCESS read-write
    STATUS current
    DESCRIPTION "Lock Device"
    ::= { paramEntry 8 }

locate OBJECT-TYPE
    SYNTAX OnOffValue
    MAX-ACCESS read-write
    STATUS current
    DESCRIPTION "toggle the locating function (yellow flashing master LED) ON/OFF"
    ::= { paramEntry 9 }

backpanelStatus OBJECT-TYPE
    SYNTAX TypeBackpanelStatus
    MAX-ACCESS read-only
    STATUS current
    DESCRIPTION "Presence indication of the device backpanel"
    ::= { paramEntry 10 }

boardID OBJECT-TYPE
    SYNTAX Integer32
    MAX-ACCESS read-only
    STATUS current
    DESCRIPTION "BoardID"
    ::= { paramEntry 11 }

outStandard OBJECT-TYPE
    SYNTAX TypeOutStandard
    MAX-ACCESS read-only
    STATUS current
    DESCRIPTION "Video standard of SDI output"
    ::= { paramEntry 14 }

inStandard OBJECT-TYPE
    SYNTAX TypeOutStandard
    MAX-ACCESS read-only
    STATUS current
    DESCRIPTION "SDI input status indication"
    ::= { paramEntry 15 }

delayVideoUserMode OBJECT-TYPE
    SYNTAX TypeDelayVideoUserMode
    MAX-ACCESS read-write
    STATUS current
    DESCRIPTION "User-defined video delay control mode (frames / lines / pixels or milliseconds)"
    ::= { paramEntry 16 }

delayVideoFrames OBJECT-TYPE
    SYNTAX Integer32
    MAX-ACCESS read-write
    STATUS current
    DESCRIPTION "SDI output delay in frames. Combine with Delay/Video/Lines and Delay/Video/Pixels for total delay"
    ::= { paramEntry 17 }

delayVideoLines OBJECT-TYPE
    SYNTAX Integer32
    MAX-ACCESS read-write
    STATUS current
    DESCRIPTION "SDI output delay in lines. Combine with Delay/Video/Frames and Delay/Video/Pixels for total delay"
    ::= { paramEntry 18 }

delayVideoPixels OBJECT-TYPE
    SYNTAX Integer32
    MAX-ACCESS read-write
    STATUS current
    DESCRIPTION "SDI output delay in pixels. Combine with Delay/Video/Frames and Delay/Video/Lines for total delay"
    ::= { paramEntry 19 }

delayVideoTotalMs OBJECT-TYPE
    SYNTAX FixedPointValue3
    MAX-ACCESS read-write
    STATUS current
    DESCRIPTION "Total SDI output delay in milliseconds"
    ::= { paramEntry 20 }

referenceLock OBJECT-TYPE
    SYNTAX TypeReferenceLock
    MAX-ACCESS read-write
    STATUS current
    DESCRIPTION "Lock all outputs to one of *RefIn *SDI1In *SDI2In"
    ::= { paramEntry 21 }

referenceStatus OBJECT-TYPE
    SYNTAX TypeOutStandard
    MAX-ACCESS read-only
    STATUS current
    DESCRIPTION "Video Standard of Reference Input"
    ::= { paramEntry 22 }

referenceSource OBJECT-TYPE
    SYNTAX TypeReferenceSource
    MAX-ACCESS read-write
    STATUS current
    DESCRIPTION "Reference Source: extern (local boards backpanel) or intern (central rack distribution)"
    ::= { paramEntry 23 }

freqPreselect OBJECT-TYPE
    SYNTAX TypeFreqPreselect
    MAX-ACCESS read-write
    STATUS current
    DESCRIPTION "Specify the frequency domain for the complete device (inputs, reference and outputs)"
    ::= { paramEntry 24 }

freq OBJECT-TYPE
    SYNTAX TypeFreq
    MAX-ACCESS read-only
    STATUS current
    DESCRIPTION "readonly information about current internal frequency (if FreqPreselect is set to follow Reference)"
    ::= { paramEntry 25 }

gPIFunc OBJECT-TYPE
    SYNTAX TypeGPIFunc
    MAX-ACCESS read-write
    STATUS current
    DESCRIPTION "Specify influence of GPI input"
    ::= { paramEntry 26 }

gPI2Func OBJECT-TYPE
    SYNTAX TypeGPIFunc
    MAX-ACCESS read-write
    STATUS current
    DESCRIPTION "Specify influence of GPI input 2"
    ::= { paramEntry 27 }

inputToRefTolerance OBJECT-TYPE
    SYNTAX OnOffValue
    MAX-ACCESS read-write
    STATUS current
    DESCRIPTION "Open a tolerance window in the relative timing between SDI In and REF In.
To be applied for modifying the timing behavior in Framesync mode.When modified to ON, the SDI Input is accepted as aligned to REF even if it arrives up to 12usec later than REF.
See User Manual for details."
    ::= { paramEntry 28 }

syncMode1 OBJECT-TYPE
    SYNTAX TypeSyncMode1
    MAX-ACCESS read-write
    STATUS current
    DESCRIPTION "Select Synchronization Mode for SDI Channel 1"
    ::= { paramEntry 29 }

inputFreezeSDI1 OBJECT-TYPE
    SYNTAX TypeInputFreezeSDI1
    MAX-ACCESS read-write
    STATUS current
    DESCRIPTION "Specify Freeze Mode for Video input channel.
Transparent: TRS Errors are transmitted to output, no freezing
Freeze on TRS Error: Output repeats last correct frame while TRS errors received on input."
    ::= { paramEntry 30 }

syncSDIIn1 OBJECT-TYPE
    SYNTAX OnOffValue
    MAX-ACCESS read-write
    STATUS current
    DESCRIPTION "Specify that the SDI Input is synchronous to the Reference (while a static offset is allowed).
This will add an automatic audio-delay compensation according to that SDI-to-REF offset. As a result, the total Audio/Video processing delay is guaranteed to be matched.
NOTE that this setting shall NOT be activated for non-synchronous SDI inputs, because this can lead to intermittent artifacts in the audio path."
    ::= { paramEntry 31 }

out1ApertureEnable OBJECT-TYPE
    SYNTAX OnOffValue
    MAX-ACCESS read-write
    STATUS current
    DESCRIPTION "SDI Out 1: enable aperture correction"
    ::= { paramEntry 32 }

out1ApertureLevel OBJECT-TYPE
    SYNTAX Integer32
    MAX-ACCESS read-write
    STATUS current
    DESCRIPTION "SDI Out 1: aperture correction level"
    ::= { paramEntry 33 }

out1HBlank OBJECT-TYPE
    SYNTAX OnOffValue
    MAX-ACCESS read-write
    STATUS current
    DESCRIPTION "SDI Out 1: enable H-Blanking"
    ::= { paramEntry 34 }

out1VBlank OBJECT-TYPE
    SYNTAX OnOffValue
    MAX-ACCESS read-write
    STATUS current
    DESCRIPTION "SDI Out 1: enable V-Blanking"
    ::= { paramEntry 35 }

out1HFlip OBJECT-TYPE
    SYNTAX OnOffValue
    MAX-ACCESS read-write
    STATUS current
    DESCRIPTION "SDI Out 1: Mirror the output image on the vertical center axis (flip in H direction)."
    ::= { paramEntry 36 }

out1Gain OBJECT-TYPE
    SYNTAX Integer32
    MAX-ACCESS read-write
    STATUS current
    DESCRIPTION "SDI Out 1: adjust Video Gain"
    ::= { paramEntry 37 }

out1Saturation OBJECT-TYPE
    SYNTAX Integer32
    MAX-ACCESS read-write
    STATUS current
    DESCRIPTION "SDI Out 1: adjust video Saturation"
    ::= { paramEntry 38 }

out1BlackLevel OBJECT-TYPE
    SYNTAX FixedPointValue1
    MAX-ACCESS read-write
    STATUS current
    DESCRIPTION "SDI Out 1: adjust video black level (in IRE)"
    ::= { paramEntry 39 }

out1Hue OBJECT-TYPE
    SYNTAX FixedPointValue1
    MAX-ACCESS read-write
    STATUS current
    DESCRIPTION "SDI Out 1: adjust video Hue"
    ::= { paramEntry 40 }

out1TestPatternSelect OBJECT-TYPE
    SYNTAX TypeOut1TestPatternSelect
    MAX-ACCESS read-write
    STATUS current
    DESCRIPTION "SDI Out 1: test pattern preselection. Will be used when test pattern is switched on, or on auto-freeze"
    ::= { paramEntry 41 }

out1TestPatternStd OBJECT-TYPE
    SYNTAX TypeOut1TestPatternStd
    MAX-ACCESS read-write
    STATUS current
    DESCRIPTION "SDI Out 1: test pattern standard.
This is only relevant when explicitly switching the test pattern ON (parameter Out1/Test/PatternOn).Otherwise (in case of automatic freeze-to-pattern), the last input standard will be used."
    ::= { paramEntry 42 }

out1TestPatternOn OBJECT-TYPE
    SYNTAX OnOffValue
    MAX-ACCESS read-write
    STATUS current
    DESCRIPTION "SDI Out 1: enable preselected test pattern"
    ::= { paramEntry 43 }

out1IfNoInput OBJECT-TYPE
    SYNTAX TypeOut1IfNoInput
    MAX-ACCESS read-write
    STATUS current
    DESCRIPTION "SDI Out 1: specify image content if input is missing.
Setting this switch to test pattern will generate the preselected pattern if input is missing."
    ::= { paramEntry 44 }

input1OpticalSignalQuality OBJECT-TYPE
    SYNTAX FixedPointValue1
    MAX-ACCESS read-only
    STATUS current
    DESCRIPTION "Signal quality at optical SDI Input 1"
    ::= { paramEntry 45 }

sFPModuleType1 OBJECT-TYPE
    SYNTAX DisplayString
    MAX-ACCESS read-only
    STATUS current
    DESCRIPTION "displays the type of detected SFP-Module 1. The SFP part number will also be  displayed if SFP-Module is unknown."
    ::= { paramEntry 46 }

sFPModulePartNumber1 OBJECT-TYPE
    SYNTAX DisplayString
    MAX-ACCESS read-only
    STATUS current
    DESCRIPTION "Displays the part number of used SFP Module"
    ::= { paramEntry 47 }

sDIIn1SourceType OBJECT-TYPE
    SYNTAX TypeSDIIn1SourceType
    MAX-ACCESS read-write
    STATUS current
    DESCRIPTION "Select Source for SDI input 1 from electrical or optical connector"
    ::= { paramEntry 48 }

audioDelayAESOut OBJECT-TYPE
    SYNTAX FixedPointValue2
    MAX-ACCESS read-write
    STATUS current
    DESCRIPTION "additional audio delay [ms] for AES-OUT"
    ::= { paramEntry 49 }

audioDelaySDI1 OBJECT-TYPE
    SYNTAX FixedPointValue2
    MAX-ACCESS read-write
    STATUS current
    DESCRIPTION "additional audio delay [ms] for audio sourced by SDI 1"
    ::= { paramEntry 50 }

audioDelaySDIOut1 OBJECT-TYPE
    SYNTAX FixedPointValue2
    MAX-ACCESS read-write
    STATUS current
    DESCRIPTION "additional audio delay [ms] for audio sourced by SDI-Out 1"
    ::= { paramEntry 51 }

presetsGPIOn OBJECT-TYPE
    SYNTAX TypePresetsGPIOn
    MAX-ACCESS read-write
    STATUS current
    DESCRIPTION "Select user preset that will be activated when GPI is On.
That applies only if GPI Influence is set to switch User presets."
    ::= { paramEntry 52 }

presetsGPIOff OBJECT-TYPE
    SYNTAX TypePresetsGPIOn
    MAX-ACCESS read-write
    STATUS current
    DESCRIPTION "Select user preset that will be activated when GPI is Off.
That applies only if GPI Influence is set to switch User presets."
    ::= { paramEntry 53 }

presetsGPIOffOn OBJECT-TYPE
    SYNTAX TypePresetsGPIOn
    MAX-ACCESS read-write
    STATUS current
    DESCRIPTION "Select user preset that will be activated when GPI 1 is Off and GPI 2 is On.
That applies only if both GPI Influence parameters are set to switch User presets."
    ::= { paramEntry 54 }

presetsGPIOnOn OBJECT-TYPE
    SYNTAX TypePresetsGPIOn
    MAX-ACCESS read-write
    STATUS current
    DESCRIPTION "Select user preset that will be activated when both GPIs are On. 
That applies only if both GPI Influence parameters are set to switch User presets."
    ::= { paramEntry 55 }

inputToRefDelay1H OBJECT-TYPE
    SYNTAX Integer32
    MAX-ACCESS read-only
    STATUS current
    DESCRIPTION "InputToRefDelay1H"
    ::= { paramEntry 56 }

inputToRefDelay1V OBJECT-TYPE
    SYNTAX Integer32
    MAX-ACCESS read-only
    STATUS current
    DESCRIPTION "InputToRefDelay1V"
    ::= { paramEntry 57 }

out1ClipHeadroom OBJECT-TYPE
    SYNTAX OnOffValue
    MAX-ACCESS read-write
    STATUS current
    DESCRIPTION "SDI Out 1: Clips Y code values outside the range of 40h to 3ACh
 and Cr, Cb code values outside the range of 40h to 3C0h."
    ::= { paramEntry 58 }

out1FreezeMode OBJECT-TYPE
    SYNTAX TypeOut1FreezeMode
    MAX-ACCESS read-write
    STATUS current
    DESCRIPTION "SDI Out 1: specify freeze mode if input is missing."
    ::= { paramEntry 59 }

out1TotalProcTime OBJECT-TYPE
    SYNTAX FixedPointValue3
    MAX-ACCESS read-write
    STATUS current
    DESCRIPTION "Show the total delay comprising the processing time and the user delay <br>on the used path from SDI Input to SDI Output 1"
    ::= { paramEntry 60 }

statusColor OBJECT-TYPE
    SYNTAX TypeStatusColor
    MAX-ACCESS read-only
    STATUS current
    DESCRIPTION "The current color of the Devices Master LED (red/green/yellow)"
    ::= { paramEntry 66 }

statusColorRGB OBJECT-TYPE
    SYNTAX DisplayString
    MAX-ACCESS read-only
    STATUS current
    DESCRIPTION "The current color of the Devices Master LED as #RRGGBB"
    ::= { paramEntry 67 }

statusText OBJECT-TYPE
    SYNTAX DisplayString
    MAX-ACCESS read-only
    STATUS current
    DESCRIPTION "The current status text (OK or error-details)"
    ::= { paramEntry 68 }

eventPrimaryPowermissing OBJECT-TYPE
    SYNTAX OnOffValue
    MAX-ACCESS read-only
    STATUS current
    DESCRIPTION "Info Event: Primary Power missing"
    ::= { paramEntry 69 }

eventRedundantPowermissing OBJECT-TYPE
    SYNTAX OnOffValue
    MAX-ACCESS read-only
    STATUS current
    DESCRIPTION "Info Event: Redundant Power missing"
    ::= { paramEntry 70 }

eventFanFailure OBJECT-TYPE
    SYNTAX OnOffValue
    MAX-ACCESS read-only
    STATUS current
    DESCRIPTION "Error Event: Fan Failure"
    ::= { paramEntry 71 }

eventReferenceNoInput OBJECT-TYPE
    SYNTAX OnOffValue
    MAX-ACCESS read-only
    STATUS current
    DESCRIPTION "Info Event: Reference No Input"
    ::= { paramEntry 72 }

eventSDIInput1NoInput OBJECT-TYPE
    SYNTAX OnOffValue
    MAX-ACCESS read-only
    STATUS current
    DESCRIPTION "Error Event: SDI Input 1 No Input"
    ::= { paramEntry 73 }

eventCouldnotlocktoReference OBJECT-TYPE
    SYNTAX OnOffValue
    MAX-ACCESS read-only
    STATUS current
    DESCRIPTION "Info Event: Could not lock to Reference"
    ::= { paramEntry 74 }

eventCouldnotlocktoSDIInput1 OBJECT-TYPE
    SYNTAX OnOffValue
    MAX-ACCESS read-only
    STATUS current
    DESCRIPTION "Warning Event: Could not lock to SDI Input 1"
    ::= { paramEntry 75 }

presetsNumber OBJECT-TYPE
    SYNTAX Integer32
    MAX-ACCESS read-only
    STATUS current
    DESCRIPTION "maximum number of user presets"
    ::= { paramEntry 77 }

presetsActive OBJECT-TYPE
    SYNTAX TypePresetsGPIOn
    MAX-ACCESS read-write
    STATUS current
    DESCRIPTION "Select the Active Preset.<br>NOTE: manual modifications to individual processing parameters are only possible if the Active Preset is set to #0. You can load any Preset into #0 (aka <i>Current</i>) and make the required modifications there."
    ::= { paramEntry 78 }

presetsSaveAs OBJECT-TYPE
    SYNTAX TypePresetsSaveAs
    MAX-ACCESS read-write
    STATUS current
    DESCRIPTION "saves the current user settings as a user preset, that saved user preset can be later loaded again into the current settings"
    ::= { paramEntry 79 }

presetsCurrentSettingsBasedOn OBJECT-TYPE
    SYNTAX TypePresetsCurrentSettingsBasedOn
    MAX-ACCESS read-only
    STATUS current
    DESCRIPTION "Current Settings based on"
    ::= { paramEntry 80 }

presetsLoadToCurrent OBJECT-TYPE
    SYNTAX TypePresetsCurrentSettingsBasedOn
    MAX-ACCESS read-write
    STATUS current
    DESCRIPTION "Load a copy of the specified UserPreset as the current settings.<br>The current settings of the complete product will be overwritten. Reading the current value of this parameter tells you which of the available presets has been loaded last.<br>NOTE that the current settings can potentially differ from the loaded preset because individual changes may have been applied at any time."
    ::= { paramEntry 81 }

presetsName0 OBJECT-TYPE
    SYNTAX DisplayString
    MAX-ACCESS read-write
    STATUS current
    DESCRIPTION "name of user preset 0"
    ::= { paramEntry 82 }

presetsName1 OBJECT-TYPE
    SYNTAX DisplayString
    MAX-ACCESS read-write
    STATUS current
    DESCRIPTION "name of user preset 1"
    ::= { paramEntry 83 }

presetsName2 OBJECT-TYPE
    SYNTAX DisplayString
    MAX-ACCESS read-write
    STATUS current
    DESCRIPTION "name of user preset 2"
    ::= { paramEntry 84 }

presetsName3 OBJECT-TYPE
    SYNTAX DisplayString
    MAX-ACCESS read-write
    STATUS current
    DESCRIPTION "name of user preset 3"
    ::= { paramEntry 85 }

presetsName4 OBJECT-TYPE
    SYNTAX DisplayString
    MAX-ACCESS read-write
    STATUS current
    DESCRIPTION "name of user preset 4"
    ::= { paramEntry 86 }

presetsName5 OBJECT-TYPE
    SYNTAX DisplayString
    MAX-ACCESS read-write
    STATUS current
    DESCRIPTION "name of user preset 5"
    ::= { paramEntry 87 }

presetsName6 OBJECT-TYPE
    SYNTAX DisplayString
    MAX-ACCESS read-write
    STATUS current
    DESCRIPTION "name of user preset 6"
    ::= { paramEntry 88 }

presetsName7 OBJECT-TYPE
    SYNTAX DisplayString
    MAX-ACCESS read-write
    STATUS current
    DESCRIPTION "name of user preset 7"
    ::= { paramEntry 89 }

delayAudioSDIOutGang OBJECT-TYPE
    SYNTAX OnOffValue
    MAX-ACCESS read-write
    STATUS current
    DESCRIPTION "Gang-Mode: Couple all SDI Out Delay values (modify all delay controls synchronously)"
    ::= { paramEntry 90 }

delayAudioAESOutGang OBJECT-TYPE
    SYNTAX OnOffValue
    MAX-ACCESS read-write
    STATUS current
    DESCRIPTION "Gang-Mode: Couple all AES Out Delay values (modify all delay controls synchronously)"
    ::= { paramEntry 91 }

eventPrimaryPowermissingSNMP OBJECT-TYPE
    SYNTAX TypeEventPrimaryPowermissingSNMP
    MAX-ACCESS read-write
    STATUS current
    DESCRIPTION "SNMP Trap for  Event: Primary Power missing"
    ::= { paramEntry 93 }

eventRedundantPowermissingSNMP OBJECT-TYPE
    SYNTAX TypeEventPrimaryPowermissingSNMP
    MAX-ACCESS read-write
    STATUS current
    DESCRIPTION "SNMP Trap for  Event: Redundant Power missing"
    ::= { paramEntry 94 }

eventFanFailureSNMP OBJECT-TYPE
    SYNTAX TypeEventPrimaryPowermissingSNMP
    MAX-ACCESS read-write
    STATUS current
    DESCRIPTION "SNMP Trap for  Event: Fan Failure"
    ::= { paramEntry 95 }

eventReferenceNoInputSNMP OBJECT-TYPE
    SYNTAX TypeEventPrimaryPowermissingSNMP
    MAX-ACCESS read-write
    STATUS current
    DESCRIPTION "SNMP Trap for  Event: Reference No Input"
    ::= { paramEntry 96 }

eventSDIInput1NoInputSNMP OBJECT-TYPE
    SYNTAX TypeEventPrimaryPowermissingSNMP
    MAX-ACCESS read-write
    STATUS current
    DESCRIPTION "SNMP Trap for  Event: SDI Input 1 No Input"
    ::= { paramEntry 97 }

eventCouldnotlocktoReferenceSNMP OBJECT-TYPE
    SYNTAX TypeEventPrimaryPowermissingSNMP
    MAX-ACCESS read-write
    STATUS current
    DESCRIPTION "SNMP Trap for  Event: Could not lock to Reference"
    ::= { paramEntry 98 }

eventCouldnotlocktoSDIInput1SNMP OBJECT-TYPE
    SYNTAX TypeEventPrimaryPowermissingSNMP
    MAX-ACCESS read-write
    STATUS current
    DESCRIPTION "SNMP Trap for  Event: Could not lock to SDI Input 1"
    ::= { paramEntry 99 }

metaVPIDStandardConform OBJECT-TYPE
    SYNTAX OnOffValue
    MAX-ACCESS read-write
    STATUS current
    DESCRIPTION "Specify whether the line for VPID insertion into Field2 is set according to the SMPTE 352M-2002 Standard or not."
    ::= { paramEntry 100 }

sDIIn13GFormat OBJECT-TYPE
    SYNTAX TypeSDIIn13GFormat
    MAX-ACCESS read-only
    STATUS current
    DESCRIPTION "For 3G-SDI input streams, this value displays the mapping format according to SMPTE 425."
    ::= { paramEntry 101 }

sDIIn1DeembedFrom3GLevelB OBJECT-TYPE
    SYNTAX TypeSDIIn1DeembedFrom3GLevelB
    MAX-ACCESS read-write
    STATUS current
    DESCRIPTION "For 3G-SDI input streams in Dual-Link or Dual-Stream mapping, the audio-deembedder will work on the selected stream only."
    ::= { paramEntry 102 }

out13GFormat OBJECT-TYPE
    SYNTAX TypeOut13GFormat
    MAX-ACCESS read-only
    STATUS current
    DESCRIPTION "For 3G-SDI output streams, this parameter shows the current format."
    ::= { paramEntry 103 }

out1SDI3GTransport OBJECT-TYPE
    SYNTAX TypeOut1SDI3GTransport
    MAX-ACCESS read-write
    STATUS current
    DESCRIPTION "For 3G-SDI output streams, select the desired transport format.<br>The default behaviour (auto) will chose the same transport format as the input stream, resp. fall back to <i>Level A</i>."
    ::= { paramEntry 104 }

out1Embed3GLevelBStreamSelect OBJECT-TYPE
    SYNTAX TypeOut1Embed3GLevelBStreamSelect
    MAX-ACCESS read-write
    STATUS current
    DESCRIPTION "For 3G-SDI multi-stream output formats, specify which streams to embed audio into.<br>By default, the same audio content is embedded into both streams. Note: if only one stream is specified, then the same groups will be removed from the other stream.<br>NOTE: see also parameter OutX/EmbedStreamCP."
    ::= { paramEntry 105 }

out1Embed3GLevelBCPStreamSelect OBJECT-TYPE
    SYNTAX TypeOut1Embed3GLevelBStreamSelect
    MAX-ACCESS read-write
    STATUS current
    DESCRIPTION "For 3G-SDI multi-stream output formats, specify which streams to embed audio control packets into.<br>By default, the audio control packets are embedded into stream A only.<br>NOTE: see also parameter OutX/EmbedStream."
    ::= { paramEntry 106 }

sFPOutPower OBJECT-TYPE
    SYNTAX DisplayString
    MAX-ACCESS read-only
    STATUS current
    DESCRIPTION "displays the average output power of detected SFP-Module ."
    ::= { paramEntry 107 }

sFPWavelength OBJECT-TYPE
    SYNTAX DisplayString
    MAX-ACCESS read-only
    STATUS current
    DESCRIPTION "displays the wavelength of detected SFP-Module ."
    ::= { paramEntry 108 }

sNumber OBJECT-TYPE
    SYNTAX DisplayString
    MAX-ACCESS read-only
    STATUS current
    DESCRIPTION "Serial Number"
    ::= { paramEntry 109 }

-- Parameter table
paramTable OBJECT-TYPE
    SYNTAX SEQUENCE OF ParamEntry
    MAX-ACCESS not-accessible
    STATUS current
    DESCRIPTION "Table of PVD5800-O parameters"
    ::= { sw762 1 }

paramEntry OBJECT-TYPE
    SYNTAX ParamEntry
    MAX-ACCESS not-accessible
    STATUS current
    DESCRIPTION "A row in the table of PVD5800-O parameters"
    INDEX { IMPLIED position }
    ::= { paramTable 1 }

ParamEntry ::= SEQUENCE {
    typeName DisplayString,
    displayName DisplayString,
    position OCTET STRING,
    uptime TimeTicks,
    type DisplayString,
    version DisplayString,
    factoryReset TypeFactoryReset,
    lock OnOffValue,
    locate OnOffValue,
    backpanelStatus TypeBackpanelStatus,
    boardID Integer32,
    outStandard TypeOutStandard,
    inStandard TypeOutStandard,
    delayVideoUserMode TypeDelayVideoUserMode,
    delayVideoFrames Integer32,
    delayVideoLines Integer32,
    delayVideoPixels Integer32,
    delayVideoTotalMs FixedPointValue3,
    referenceLock TypeReferenceLock,
    referenceStatus TypeOutStandard,
    referenceSource TypeReferenceSource,
    freqPreselect TypeFreqPreselect,
    freq TypeFreq,
    gPIFunc TypeGPIFunc,
    gPI2Func TypeGPIFunc,
    inputToRefTolerance OnOffValue,
    syncMode1 TypeSyncMode1,
    inputFreezeSDI1 TypeInputFreezeSDI1,
    syncSDIIn1 OnOffValue,
    out1ApertureEnable OnOffValue,
    out1ApertureLevel Integer32,
    out1HBlank OnOffValue,
    out1VBlank OnOffValue,
    out1HFlip OnOffValue,
    out1Gain Integer32,
    out1Saturation Integer32,
    out1BlackLevel FixedPointValue1,
    out1Hue FixedPointValue1,
    out1TestPatternSelect TypeOut1TestPatternSelect,
    out1TestPatternStd TypeOut1TestPatternStd,
    out1TestPatternOn OnOffValue,
    out1IfNoInput TypeOut1IfNoInput,
    input1OpticalSignalQuality FixedPointValue1,
    sFPModuleType1 DisplayString,
    sFPModulePartNumber1 DisplayString,
    sDIIn1SourceType TypeSDIIn1SourceType,
    audioDelayAESOut FixedPointValue2,
    audioDelaySDI1 FixedPointValue2,
    audioDelaySDIOut1 FixedPointValue2,
    presetsGPIOn TypePresetsGPIOn,
    presetsGPIOff TypePresetsGPIOn,
    presetsGPIOffOn TypePresetsGPIOn,
    presetsGPIOnOn TypePresetsGPIOn,
    inputToRefDelay1H Integer32,
    inputToRefDelay1V Integer32,
    out1ClipHeadroom OnOffValue,
    out1FreezeMode TypeOut1FreezeMode,
    out1TotalProcTime FixedPointValue3,
    statusColor TypeStatusColor,
    statusColorRGB DisplayString,
    statusText DisplayString,
    eventPrimaryPowermissing OnOffValue,
    eventRedundantPowermissing OnOffValue,
    eventFanFailure OnOffValue,
    eventReferenceNoInput OnOffValue,
    eventSDIInput1NoInput OnOffValue,
    eventCouldnotlocktoReference OnOffValue,
    eventCouldnotlocktoSDIInput1 OnOffValue,
    presetsNumber Integer32,
    presetsActive TypePresetsGPIOn,
    presetsSaveAs TypePresetsSaveAs,
    presetsCurrentSettingsBasedOn TypePresetsCurrentSettingsBasedOn,
    presetsLoadToCurrent TypePresetsCurrentSettingsBasedOn,
    presetsName0 DisplayString,
    presetsName1 DisplayString,
    presetsName2 DisplayString,
    presetsName3 DisplayString,
    presetsName4 DisplayString,
    presetsName5 DisplayString,
    presetsName6 DisplayString,
    presetsName7 DisplayString,
    delayAudioSDIOutGang OnOffValue,
    delayAudioAESOutGang OnOffValue,
    eventPrimaryPowermissingSNMP TypeEventPrimaryPowermissingSNMP,
    eventRedundantPowermissingSNMP TypeEventPrimaryPowermissingSNMP,
    eventFanFailureSNMP TypeEventPrimaryPowermissingSNMP,
    eventReferenceNoInputSNMP TypeEventPrimaryPowermissingSNMP,
    eventSDIInput1NoInputSNMP TypeEventPrimaryPowermissingSNMP,
    eventCouldnotlocktoReferenceSNMP TypeEventPrimaryPowermissingSNMP,
    eventCouldnotlocktoSDIInput1SNMP TypeEventPrimaryPowermissingSNMP,
    metaVPIDStandardConform OnOffValue,
    sDIIn13GFormat TypeSDIIn13GFormat,
    sDIIn1DeembedFrom3GLevelB TypeSDIIn1DeembedFrom3GLevelB,
    out13GFormat TypeOut13GFormat,
    out1SDI3GTransport TypeOut1SDI3GTransport,
    out1Embed3GLevelBStreamSelect TypeOut1Embed3GLevelBStreamSelect,
    out1Embed3GLevelBCPStreamSelect TypeOut1Embed3GLevelBStreamSelect,
    sFPOutPower DisplayString,
    sFPWavelength DisplayString,
    sNumber DisplayString }

-- Conformance statements
conformance OBJECT-IDENTITY
    STATUS current
    DESCRIPTION "Conformance declaration of PVD5800-O"
    ::= { sw762 2 }

paramGroup OBJECT-GROUP
    OBJECTS {
        typeName,
        displayName,
        position,
        uptime,
        type,
        version,
        factoryReset,
        lock,
        locate,
        backpanelStatus,
        boardID,
        outStandard,
        inStandard,
        delayVideoUserMode,
        delayVideoFrames,
        delayVideoLines,
        delayVideoPixels,
        delayVideoTotalMs,
        referenceLock,
        referenceStatus,
        referenceSource,
        freqPreselect,
        freq,
        gPIFunc,
        gPI2Func,
        inputToRefTolerance,
        syncMode1,
        inputFreezeSDI1,
        syncSDIIn1,
        out1ApertureEnable,
        out1ApertureLevel,
        out1HBlank,
        out1VBlank,
        out1HFlip,
        out1Gain,
        out1Saturation,
        out1BlackLevel,
        out1Hue,
        out1TestPatternSelect,
        out1TestPatternStd,
        out1TestPatternOn,
        out1IfNoInput,
        input1OpticalSignalQuality,
        sFPModuleType1,
        sFPModulePartNumber1,
        sDIIn1SourceType,
        audioDelayAESOut,
        audioDelaySDI1,
        audioDelaySDIOut1,
        presetsGPIOn,
        presetsGPIOff,
        presetsGPIOffOn,
        presetsGPIOnOn,
        inputToRefDelay1H,
        inputToRefDelay1V,
        out1ClipHeadroom,
        out1FreezeMode,
        out1TotalProcTime,
        statusColor,
        statusColorRGB,
        statusText,
        eventPrimaryPowermissing,
        eventRedundantPowermissing,
        eventFanFailure,
        eventReferenceNoInput,
        eventSDIInput1NoInput,
        eventCouldnotlocktoReference,
        eventCouldnotlocktoSDIInput1,
        presetsNumber,
        presetsActive,
        presetsSaveAs,
        presetsCurrentSettingsBasedOn,
        presetsLoadToCurrent,
        presetsName0,
        presetsName1,
        presetsName2,
        presetsName3,
        presetsName4,
        presetsName5,
        presetsName6,
        presetsName7,
        delayAudioSDIOutGang,
        delayAudioAESOutGang,
        eventPrimaryPowermissingSNMP,
        eventRedundantPowermissingSNMP,
        eventFanFailureSNMP,
        eventReferenceNoInputSNMP,
        eventSDIInput1NoInputSNMP,
        eventCouldnotlocktoReferenceSNMP,
        eventCouldnotlocktoSDIInput1SNMP,
        metaVPIDStandardConform,
        sDIIn13GFormat,
        sDIIn1DeembedFrom3GLevelB,
        out13GFormat,
        out1SDI3GTransport,
        out1Embed3GLevelBStreamSelect,
        out1Embed3GLevelBCPStreamSelect,
        sFPOutPower,
        sFPWavelength,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
