-- Machine generated MIB file, do not edit!
--
-- MIB file for ORX5800, type code 08.DC, software label 619
-- Generated on Tuesday, 09-Aug-16 14:44:17 UTC
-- CVS $Id: ORX5800_08dc_sw619.mib,v 1.4 2016/08/09 14:44:19 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

ORX5800-08dc-sw619-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

orx5800-08dc-sw619 MODULE-IDENTITY
    LAST-UPDATED "201608091444Z"
    ORGANIZATION "LYNX Technik AG"
    CONTACT-INFO "LYNX Technik AG
        Brunnenweg 3
        64331 Weiterstadt
        http://www.lynx-technik.com
        mailto:support@lynx-technik.com"
    DESCRIPTION "MIB module definition for ORX5800, type code 08.DC, software label 619"
    REVISION "201608091444Z"
    DESCRIPTION "Generated by LYNX Asset Database"
    ::= { mib-modules 2268619 }

orx5800-08dc OBJECT-IDENTITY
    STATUS current
    DESCRIPTION "LYNX device type ORX5800"
    ::= { products 2268 }

sw619 OBJECT-IDENTITY
    STATUS current
    DESCRIPTION "Software label 619"
    ::= { orx5800-08dc 619 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeSourceInput1 ::= TEXTUAL-CONVENTION
    STATUS current
    DESCRIPTION "Enumeration"
    SYNTAX INTEGER {
        optical(0),
        electrical(1)
    }

TypeIn1 ::= TEXTUAL-CONVENTION
    STATUS current
    DESCRIPTION "Enumeration"
    SYNTAX INTEGER {
        missing(0),
        sDSDI(1),
        hDSDI(2),
        n3GSDI(3),
        hD3G(4),
        present(5)
    }

TypeSignalType ::= TEXTUAL-CONVENTION
    STATUS current
    DESCRIPTION "Enumeration"
    SYNTAX INTEGER {
        slow(0),
        fast(1)
    }

TypeSourceOut1 ::= TEXTUAL-CONVENTION
    STATUS current
    DESCRIPTION "Enumeration"
    SYNTAX INTEGER {
        in1(0),
        in2(1),
        in3(2),
        in4(3)
    }

TypeEventPrimaryPowermissingSNMP ::= TEXTUAL-CONVENTION
    STATUS current
    DESCRIPTION "Enumeration"
    SYNTAX INTEGER {
        none(0),
        onOnly(1),
        offOnly(2),
        onOff(3)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

boardID OBJECT-TYPE
    SYNTAX Integer32
    MAX-ACCESS read-only
    STATUS current
    DESCRIPTION "BoardID"
    ::= { paramEntry 13 }

eventSDIInput1NoInput OBJECT-TYPE
    SYNTAX OnOffValue
    MAX-ACCESS read-only
    STATUS current
    DESCRIPTION "SDI Input 1: No Input"
    ::= { paramEntry 15 }

eventSDIInput2NoInput OBJECT-TYPE
    SYNTAX OnOffValue
    MAX-ACCESS read-only
    STATUS current
    DESCRIPTION "SDI Input 2: No Input"
    ::= { paramEntry 16 }

eventSDIInput3NoInput OBJECT-TYPE
    SYNTAX OnOffValue
    MAX-ACCESS read-only
    STATUS current
    DESCRIPTION "SDI Input 3: No Input"
    ::= { paramEntry 17 }

eventSDIInput4NoInput OBJECT-TYPE
    SYNTAX OnOffValue
    MAX-ACCESS read-only
    STATUS current
    DESCRIPTION "SDI Input 4: No Input"
    ::= { paramEntry 18 }

eventPrimaryPowermissing OBJECT-TYPE
    SYNTAX OnOffValue
    MAX-ACCESS read-only
    STATUS current
    DESCRIPTION "Info Event: Primary Power missing"
    ::= { paramEntry 19 }

eventRedundantPowermissing OBJECT-TYPE
    SYNTAX OnOffValue
    MAX-ACCESS read-only
    STATUS current
    DESCRIPTION "Info Event: Redundant Power missing"
    ::= { paramEntry 20 }

sourceInput1 OBJECT-TYPE
    SYNTAX TypeSourceInput1
    MAX-ACCESS read-write
    STATUS current
    DESCRIPTION "Select Source for Input 1 from electrical or optical connector"
    ::= { paramEntry 21 }

sourceInput4 OBJECT-TYPE
    SYNTAX TypeSourceInput1
    MAX-ACCESS read-write
    STATUS current
    DESCRIPTION "Select Source for Input 4 from electrical or optical connector"
    ::= { paramEntry 22 }

in1 OBJECT-TYPE
    SYNTAX TypeIn1
    MAX-ACCESS read-only
    STATUS current
    DESCRIPTION "Input status channel 1"
    ::= { paramEntry 23 }

in2 OBJECT-TYPE
    SYNTAX TypeIn1
    MAX-ACCESS read-only
    STATUS current
    DESCRIPTION "Input status channel 2"
    ::= { paramEntry 24 }

in3 OBJECT-TYPE
    SYNTAX TypeIn1
    MAX-ACCESS read-only
    STATUS current
    DESCRIPTION "Input status channel 3"
    ::= { paramEntry 25 }

in4 OBJECT-TYPE
    SYNTAX TypeIn1
    MAX-ACCESS read-only
    STATUS current
    DESCRIPTION "Input status channel 4"
    ::= { paramEntry 26 }

out1 OBJECT-TYPE
    SYNTAX TypeIn1
    MAX-ACCESS read-only
    STATUS current
    DESCRIPTION "Output status channel 1"
    ::= { paramEntry 27 }

out2 OBJECT-TYPE
    SYNTAX TypeIn1
    MAX-ACCESS read-only
    STATUS current
    DESCRIPTION "Output status channel 2"
    ::= { paramEntry 28 }

out3 OBJECT-TYPE
    SYNTAX TypeIn1
    MAX-ACCESS read-only
    STATUS current
    DESCRIPTION "Output status channel 3"
    ::= { paramEntry 29 }

out4 OBJECT-TYPE
    SYNTAX TypeIn1
    MAX-ACCESS read-only
    STATUS current
    DESCRIPTION "Output status channel 4"
    ::= { paramEntry 30 }

signalType OBJECT-TYPE
    SYNTAX TypeSignalType
    MAX-ACCESS read-write
    STATUS current
    DESCRIPTION "This switch configures the slew rate (rise/fall time) of all output signals that are connected to such input(s) where the reclocker is manually switched off.
In this case (reclocker off), the signal speed cannot be detected automatically and therefore the output configuration has to be set manually with this switch."
    ::= { paramEntry 31 }

reclock1 OBJECT-TYPE
    SYNTAX OnOffValue
    MAX-ACCESS read-write
    STATUS current
    DESCRIPTION "select SDI reclocking on input 1"
    ::= { paramEntry 32 }

reclock2 OBJECT-TYPE
    SYNTAX OnOffValue
    MAX-ACCESS read-write
    STATUS current
    DESCRIPTION "select SDI reclocking on input 2"
    ::= { paramEntry 33 }

reclock3 OBJECT-TYPE
    SYNTAX OnOffValue
    MAX-ACCESS read-write
    STATUS current
    DESCRIPTION "select SDI reclocking on input 3"
    ::= { paramEntry 34 }

reclock4 OBJECT-TYPE
    SYNTAX OnOffValue
    MAX-ACCESS read-write
    STATUS current
    DESCRIPTION "select SDI reclocking on input 4"
    ::= { paramEntry 35 }

input1OpticalSignalQuality OBJECT-TYPE
    SYNTAX FixedPointValue1
    MAX-ACCESS read-only
    STATUS current
    DESCRIPTION "Signal quality at optical SDI Input 1"
    ::= { paramEntry 36 }

input2OpticalSignalQuality OBJECT-TYPE
    SYNTAX FixedPointValue1
    MAX-ACCESS read-only
    STATUS current
    DESCRIPTION "Signal quality at optical SDI Input 2"
    ::= { paramEntry 37 }

input3OpticalSignalQuality OBJECT-TYPE
    SYNTAX FixedPointValue1
    MAX-ACCESS read-only
    STATUS current
    DESCRIPTION "Signal quality at optical SDI Input 3"
    ::= { paramEntry 38 }

input4OpticalSignalQuality OBJECT-TYPE
    SYNTAX FixedPointValue1
    MAX-ACCESS read-only
    STATUS current
    DESCRIPTION "Signal quality at optical SDI Input 4"
    ::= { paramEntry 39 }

sFPModuleType1 OBJECT-TYPE
    SYNTAX DisplayString
    MAX-ACCESS read-only
    STATUS current
    DESCRIPTION "displays the type of detected SFP-Module 1. The SFP part number will also be  displayed if SFP-Module is unknown."
    ::= { paramEntry 40 }

sFPModulePartNumber1 OBJECT-TYPE
    SYNTAX DisplayString
    MAX-ACCESS read-only
    STATUS current
    DESCRIPTION "Displays the part number of used SFP Module"
    ::= { paramEntry 41 }

sFPModuleType2 OBJECT-TYPE
    SYNTAX DisplayString
    MAX-ACCESS read-only
    STATUS current
    DESCRIPTION "displays the type of detected SFP-Module 2. The SFP part number will also be  displayed if SFP-Module is unknown."
    ::= { paramEntry 42 }

sFPModulePartNumber2 OBJECT-TYPE
    SYNTAX DisplayString
    MAX-ACCESS read-only
    STATUS current
    DESCRIPTION "Displays the part number of used SFP Module"
    ::= { paramEntry 43 }

sourceOut1 OBJECT-TYPE
    SYNTAX TypeSourceOut1
    MAX-ACCESS read-write
    STATUS current
    DESCRIPTION "Select Source stream for output 1 from input 1 or 2"
    ::= { paramEntry 44 }

sourceOut2 OBJECT-TYPE
    SYNTAX TypeSourceOut1
    MAX-ACCESS read-write
    STATUS current
    DESCRIPTION "Select Source stream for output 2 from input 1 or 2"
    ::= { paramEntry 45 }

sourceOut3 OBJECT-TYPE
    SYNTAX TypeSourceOut1
    MAX-ACCESS read-write
    STATUS current
    DESCRIPTION "Select Source stream for output 3 from input 1 or 2"
    ::= { paramEntry 46 }

sourceOut4 OBJECT-TYPE
    SYNTAX TypeSourceOut1
    MAX-ACCESS read-write
    STATUS current
    DESCRIPTION "Select Source stream for output 4 from input 1 or 2"
    ::= { paramEntry 47 }

eventVideoInput1NoInput OBJECT-TYPE
    SYNTAX OnOffValue
    MAX-ACCESS read-only
    STATUS current
    DESCRIPTION "Warning Event: Video Input 1 No Input"
    ::= { paramEntry 48 }

eventVideoInput2NoInput OBJECT-TYPE
    SYNTAX OnOffValue
    MAX-ACCESS read-only
    STATUS current
    DESCRIPTION "Warning Event: Video Input 2 No Input"
    ::= { paramEntry 49 }

eventVideoInput3NoInput OBJECT-TYPE
    SYNTAX OnOffValue
    MAX-ACCESS read-only
    STATUS current
    DESCRIPTION "Warning Event: Video Input 3 No Input"
    ::= { paramEntry 50 }

eventVideoInput4NoInput OBJECT-TYPE
    SYNTAX OnOffValue
    MAX-ACCESS read-only
    STATUS current
    DESCRIPTION "Warning Event: Video Input 4 No Input"
    ::= { paramEntry 51 }

eventPrimaryPowermissingSNMP OBJECT-TYPE
    SYNTAX TypeEventPrimaryPowermissingSNMP
    MAX-ACCESS read-write
    STATUS current
    DESCRIPTION "SNMP Trap for  Event: Primary Power missing"
    ::= { paramEntry 52 }

eventRedundantPowermissingSNMP OBJECT-TYPE
    SYNTAX TypeEventPrimaryPowermissingSNMP
    MAX-ACCESS read-write
    STATUS current
    DESCRIPTION "SNMP Trap for  Event: Redundant Power missing"
    ::= { paramEntry 53 }

eventVideoInput1NoInputSNMP OBJECT-TYPE
    SYNTAX TypeEventPrimaryPowermissingSNMP
    MAX-ACCESS read-write
    STATUS current
    DESCRIPTION "SNMP Trap for  Event: Video Input 1 No Input"
    ::= { paramEntry 54 }

eventVideoInput2NoInputSNMP OBJECT-TYPE
    SYNTAX TypeEventPrimaryPowermissingSNMP
    MAX-ACCESS read-write
    STATUS current
    DESCRIPTION "SNMP Trap for  Event: Video Input 2 No Input"
    ::= { paramEntry 55 }

eventVideoInput3NoInputSNMP OBJECT-TYPE
    SYNTAX TypeEventPrimaryPowermissingSNMP
    MAX-ACCESS read-write
    STATUS current
    DESCRIPTION "SNMP Trap for  Event: Video Input 3 No Input"
    ::= { paramEntry 56 }

eventVideoInput4NoInputSNMP OBJECT-TYPE
    SYNTAX TypeEventPrimaryPowermissingSNMP
    MAX-ACCESS read-write
    STATUS current
    DESCRIPTION "SNMP Trap for  Event: Video Input 4 No Input"
    ::= { paramEntry 57 }

sNumber OBJECT-TYPE
    SYNTAX DisplayString
    MAX-ACCESS read-only
    STATUS current
    DESCRIPTION "Serial Number"
    ::= { paramEntry 58 }

-- Parameter table
paramTable OBJECT-TYPE
    SYNTAX SEQUENCE OF ParamEntry
    MAX-ACCESS not-accessible
    STATUS current
    DESCRIPTION "Table of ORX5800 parameters"
    ::= { sw619 1 }

paramEntry OBJECT-TYPE
    SYNTAX ParamEntry
    MAX-ACCESS not-accessible
    STATUS current
    DESCRIPTION "A row in the table of ORX5800 parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    boardID Integer32,
    eventSDIInput1NoInput OnOffValue,
    eventSDIInput2NoInput OnOffValue,
    eventSDIInput3NoInput OnOffValue,
    eventSDIInput4NoInput OnOffValue,
    eventPrimaryPowermissing OnOffValue,
    eventRedundantPowermissing OnOffValue,
    sourceInput1 TypeSourceInput1,
    sourceInput4 TypeSourceInput1,
    in1 TypeIn1,
    in2 TypeIn1,
    in3 TypeIn1,
    in4 TypeIn1,
    out1 TypeIn1,
    out2 TypeIn1,
    out3 TypeIn1,
    out4 TypeIn1,
    signalType TypeSignalType,
    reclock1 OnOffValue,
    reclock2 OnOffValue,
    reclock3 OnOffValue,
    reclock4 OnOffValue,
    input1OpticalSignalQuality FixedPointValue1,
    input2OpticalSignalQuality FixedPointValue1,
    input3OpticalSignalQuality FixedPointValue1,
    input4OpticalSignalQuality FixedPointValue1,
    sFPModuleType1 DisplayString,
    sFPModulePartNumber1 DisplayString,
    sFPModuleType2 DisplayString,
    sFPModulePartNumber2 DisplayString,
    sourceOut1 TypeSourceOut1,
    sourceOut2 TypeSourceOut1,
    sourceOut3 TypeSourceOut1,
    sourceOut4 TypeSourceOut1,
    eventVideoInput1NoInput OnOffValue,
    eventVideoInput2NoInput OnOffValue,
    eventVideoInput3NoInput OnOffValue,
    eventVideoInput4NoInput OnOffValue,
    eventPrimaryPowermissingSNMP TypeEventPrimaryPowermissingSNMP,
    eventRedundantPowermissingSNMP TypeEventPrimaryPowermissingSNMP,
    eventVideoInput1NoInputSNMP TypeEventPrimaryPowermissingSNMP,
    eventVideoInput2NoInputSNMP TypeEventPrimaryPowermissingSNMP,
    eventVideoInput3NoInputSNMP TypeEventPrimaryPowermissingSNMP,
    eventVideoInput4NoInputSNMP TypeEventPrimaryPowermissingSNMP,
    sNumber DisplayString }

-- Conformance statements
conformance OBJECT-IDENTITY
    STATUS current
    DESCRIPTION "Conformance declaration of ORX5800"
    ::= { sw619 2 }

paramGroup OBJECT-GROUP
    OBJECTS {
        typeName,
        displayName,
        position,
        uptime,
        type,
        version,
        statusColor,
        statusColorRGB,
        statusText,
        factoryReset,
        lock,
        locate,
        boardID,
        eventSDIInput1NoInput,
        eventSDIInput2NoInput,
        eventSDIInput3NoInput,
        eventSDIInput4NoInput,
        eventPrimaryPowermissing,
        eventRedundantPowermissing,
        sourceInput1,
        sourceInput4,
        in1,
        in2,
        in3,
        in4,
        out1,
        out2,
        out3,
        out4,
        signalType,
        reclock1,
        reclock2,
        reclock3,
        reclock4,
        input1OpticalSignalQuality,
        input2OpticalSignalQuality,
        input3OpticalSignalQuality,
        input4OpticalSignalQuality,
        sFPModuleType1,
        sFPModulePartNumber1,
        sFPModuleType2,
        sFPModulePartNumber2,
        sourceOut1,
        sourceOut2,
        sourceOut3,
        sourceOut4,
        eventVideoInput1NoInput,
        eventVideoInput2NoInput,
        eventVideoInput3NoInput,
        eventVideoInput4NoInput,
        eventPrimaryPowermissingSNMP,
        eventRedundantPowermissingSNMP,
        eventVideoInput1NoInputSNMP,
        eventVideoInput2NoInputSNMP,
        eventVideoInput3NoInputSNMP,
        eventVideoInput4NoInputSNMP,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
