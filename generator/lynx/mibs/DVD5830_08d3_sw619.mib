-- Machine generated MIB file, do not edit!
--
-- MIB file for DVD5830, type code 08.D3, software label 619
-- Generated on Tuesday, 09-Aug-16 14:40:25 UTC
-- CVS $Id: DVD5830_08d3_sw619.mib,v 1.5 2016/08/09 14:40:27 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

DVD5830-08d3-sw619-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

dvd5830-08d3-sw619 MODULE-IDENTITY
    LAST-UPDATED "201608091440Z"
    ORGANIZATION "LYNX Technik AG"
    CONTACT-INFO "LYNX Technik AG
        Brunnenweg 3
        64331 Weiterstadt
        http://www.lynx-technik.com
        mailto:support@lynx-technik.com"
    DESCRIPTION "MIB module definition for DVD5830, type code 08.D3, software label 619"
    REVISION "201608091440Z"
    DESCRIPTION "Generated by LYNX Asset Database"
    ::= { mib-modules 2259619 }

dvd5830-08d3 OBJECT-IDENTITY
    STATUS current
    DESCRIPTION "LYNX device type DVD5830"
    ::= { products 2259 }

sw619 OBJECT-IDENTITY
    STATUS current
    DESCRIPTION "Software label 619"
    ::= { dvd5830-08d3 619 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeIn1 ::= TEXTUAL-CONVENTION
    STATUS current
    DESCRIPTION "Enumeration"
    SYNTAX INTEGER {
        missing(0),
        sDSDI(1),
        hDSDI(2),
        n3GSDI(3),
        hD3G(4),
        present(5)
    }

TypeSourceOut1 ::= TEXTUAL-CONVENTION
    STATUS current
    DESCRIPTION "Enumeration"
    SYNTAX INTEGER {
        in1(0),
        in2(1),
        in3(2)
    }

TypeSignalType ::= TEXTUAL-CONVENTION
    STATUS current
    DESCRIPTION "Enumeration"
    SYNTAX INTEGER {
        slow(0),
        fast(1)
    }

TypeEventPrimaryPowermissingSNMP ::= TEXTUAL-CONVENTION
    STATUS current
    DESCRIPTION "Enumeration"
    SYNTAX INTEGER {
        none(0),
        onOnly(1),
        offOnly(2),
        onOff(3)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

eventSDIInput1NoInput OBJECT-TYPE
    SYNTAX OnOffValue
    MAX-ACCESS read-only
    STATUS current
    DESCRIPTION "SDI Input 1: No Input"
    ::= { paramEntry 14 }

eventSDIInput2NoInput OBJECT-TYPE
    SYNTAX OnOffValue
    MAX-ACCESS read-only
    STATUS current
    DESCRIPTION "SDI Input 2: No Input"
    ::= { paramEntry 15 }

eventSDIInput3NoInput OBJECT-TYPE
    SYNTAX OnOffValue
    MAX-ACCESS read-only
    STATUS current
    DESCRIPTION "SDI Input 3: No Input"
    ::= { paramEntry 16 }

eventPSU1Failure OBJECT-TYPE
    SYNTAX OnOffValue
    MAX-ACCESS read-only
    STATUS current
    DESCRIPTION "PSU1: Failure"
    ::= { paramEntry 17 }

eventPSU2Failure OBJECT-TYPE
    SYNTAX OnOffValue
    MAX-ACCESS read-only
    STATUS current
    DESCRIPTION "PSU2: Failure"
    ::= { paramEntry 18 }

in1 OBJECT-TYPE
    SYNTAX TypeIn1
    MAX-ACCESS read-only
    STATUS current
    DESCRIPTION "Input status channel 1"
    ::= { paramEntry 19 }

in2 OBJECT-TYPE
    SYNTAX TypeIn1
    MAX-ACCESS read-only
    STATUS current
    DESCRIPTION "Input status channel 2"
    ::= { paramEntry 20 }

in3 OBJECT-TYPE
    SYNTAX TypeIn1
    MAX-ACCESS read-only
    STATUS current
    DESCRIPTION "Input status channel 3"
    ::= { paramEntry 21 }

reclock1 OBJECT-TYPE
    SYNTAX OnOffValue
    MAX-ACCESS read-write
    STATUS current
    DESCRIPTION "select SDI reclocking on input 1"
    ::= { paramEntry 22 }

reclock2 OBJECT-TYPE
    SYNTAX OnOffValue
    MAX-ACCESS read-write
    STATUS current
    DESCRIPTION "select SDI reclocking on input 2"
    ::= { paramEntry 23 }

reclock3 OBJECT-TYPE
    SYNTAX OnOffValue
    MAX-ACCESS read-write
    STATUS current
    DESCRIPTION "select SDI reclocking on input 3"
    ::= { paramEntry 24 }

sourceOut1 OBJECT-TYPE
    SYNTAX TypeSourceOut1
    MAX-ACCESS read-write
    STATUS current
    DESCRIPTION "Select Source stream for output 1 from input 1 or 2"
    ::= { paramEntry 25 }

sourceOut2 OBJECT-TYPE
    SYNTAX TypeSourceOut1
    MAX-ACCESS read-write
    STATUS current
    DESCRIPTION "Select Source stream for output 2 from input 1 or 2"
    ::= { paramEntry 26 }

sourceOut3 OBJECT-TYPE
    SYNTAX TypeSourceOut1
    MAX-ACCESS read-write
    STATUS current
    DESCRIPTION "Select Source stream for output 3 from input 1 or 2"
    ::= { paramEntry 27 }

eventPrimaryPowermissing OBJECT-TYPE
    SYNTAX OnOffValue
    MAX-ACCESS read-only
    STATUS current
    DESCRIPTION "Info Event: Primary Power missing"
    ::= { paramEntry 28 }

eventRedundantPowermissing OBJECT-TYPE
    SYNTAX OnOffValue
    MAX-ACCESS read-only
    STATUS current
    DESCRIPTION "Info Event: Redundant Power missing"
    ::= { paramEntry 29 }

signalType OBJECT-TYPE
    SYNTAX TypeSignalType
    MAX-ACCESS read-write
    STATUS current
    DESCRIPTION "This switch configures the slew rate (rise/fall time) of all output signals that are connected to such input(s) where the reclocker is manually switched off.
In this case (reclocker off), the signal speed cannot be detected automatically and therefore the output configuration has to be set manually with this switch."
    ::= { paramEntry 30 }

boardID OBJECT-TYPE
    SYNTAX Integer32
    MAX-ACCESS read-only
    STATUS current
    DESCRIPTION "BoardID"
    ::= { paramEntry 31 }

out1 OBJECT-TYPE
    SYNTAX TypeIn1
    MAX-ACCESS read-only
    STATUS current
    DESCRIPTION "Output status channel 1"
    ::= { paramEntry 32 }

out2 OBJECT-TYPE
    SYNTAX TypeIn1
    MAX-ACCESS read-only
    STATUS current
    DESCRIPTION "Output status channel 2"
    ::= { paramEntry 33 }

out3 OBJECT-TYPE
    SYNTAX TypeIn1
    MAX-ACCESS read-only
    STATUS current
    DESCRIPTION "Output status channel 3"
    ::= { paramEntry 34 }

eventVideoInput1NoInput OBJECT-TYPE
    SYNTAX OnOffValue
    MAX-ACCESS read-only
    STATUS current
    DESCRIPTION "Warning Event: Video Input 1 No Input"
    ::= { paramEntry 35 }

eventVideoInput3NoInput OBJECT-TYPE
    SYNTAX OnOffValue
    MAX-ACCESS read-only
    STATUS current
    DESCRIPTION "Warning Event: Video Input 3 No Input"
    ::= { paramEntry 36 }

eventVideoInput4NoInput OBJECT-TYPE
    SYNTAX OnOffValue
    MAX-ACCESS read-only
    STATUS current
    DESCRIPTION "Warning Event: Video Input 4 No Input"
    ::= { paramEntry 37 }

eventPrimaryPowermissingSNMP OBJECT-TYPE
    SYNTAX TypeEventPrimaryPowermissingSNMP
    MAX-ACCESS read-write
    STATUS current
    DESCRIPTION "SNMP Trap for  Event: Primary Power missing"
    ::= { paramEntry 38 }

eventRedundantPowermissingSNMP OBJECT-TYPE
    SYNTAX TypeEventPrimaryPowermissingSNMP
    MAX-ACCESS read-write
    STATUS current
    DESCRIPTION "SNMP Trap for  Event: Redundant Power missing"
    ::= { paramEntry 39 }

eventVideoInput1NoInputSNMP OBJECT-TYPE
    SYNTAX TypeEventPrimaryPowermissingSNMP
    MAX-ACCESS read-write
    STATUS current
    DESCRIPTION "SNMP Trap for  Event: Video Input 1 No Input"
    ::= { paramEntry 40 }

eventVideoInput3NoInputSNMP OBJECT-TYPE
    SYNTAX TypeEventPrimaryPowermissingSNMP
    MAX-ACCESS read-write
    STATUS current
    DESCRIPTION "SNMP Trap for  Event: Video Input 3 No Input"
    ::= { paramEntry 41 }

eventVideoInput4NoInputSNMP OBJECT-TYPE
    SYNTAX TypeEventPrimaryPowermissingSNMP
    MAX-ACCESS read-write
    STATUS current
    DESCRIPTION "SNMP Trap for  Event: Video Input 4 No Input"
    ::= { paramEntry 42 }

sNumber OBJECT-TYPE
    SYNTAX DisplayString
    MAX-ACCESS read-only
    STATUS current
    DESCRIPTION "Serial Number"
    ::= { paramEntry 43 }

-- Parameter table
paramTable OBJECT-TYPE
    SYNTAX SEQUENCE OF ParamEntry
    MAX-ACCESS not-accessible
    STATUS current
    DESCRIPTION "Table of DVD5830 parameters"
    ::= { sw619 1 }

paramEntry OBJECT-TYPE
    SYNTAX ParamEntry
    MAX-ACCESS not-accessible
    STATUS current
    DESCRIPTION "A row in the table of DVD5830 parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    eventSDIInput1NoInput OnOffValue,
    eventSDIInput2NoInput OnOffValue,
    eventSDIInput3NoInput OnOffValue,
    eventPSU1Failure OnOffValue,
    eventPSU2Failure OnOffValue,
    in1 TypeIn1,
    in2 TypeIn1,
    in3 TypeIn1,
    reclock1 OnOffValue,
    reclock2 OnOffValue,
    reclock3 OnOffValue,
    sourceOut1 TypeSourceOut1,
    sourceOut2 TypeSourceOut1,
    sourceOut3 TypeSourceOut1,
    eventPrimaryPowermissing OnOffValue,
    eventRedundantPowermissing OnOffValue,
    signalType TypeSignalType,
    boardID Integer32,
    out1 TypeIn1,
    out2 TypeIn1,
    out3 TypeIn1,
    eventVideoInput1NoInput OnOffValue,
    eventVideoInput3NoInput OnOffValue,
    eventVideoInput4NoInput OnOffValue,
    eventPrimaryPowermissingSNMP TypeEventPrimaryPowermissingSNMP,
    eventRedundantPowermissingSNMP TypeEventPrimaryPowermissingSNMP,
    eventVideoInput1NoInputSNMP TypeEventPrimaryPowermissingSNMP,
    eventVideoInput3NoInputSNMP TypeEventPrimaryPowermissingSNMP,
    eventVideoInput4NoInputSNMP TypeEventPrimaryPowermissingSNMP,
    sNumber DisplayString }

-- Conformance statements
conformance OBJECT-IDENTITY
    STATUS current
    DESCRIPTION "Conformance declaration of DVD5830"
    ::= { sw619 2 }

paramGroup OBJECT-GROUP
    OBJECTS {
        typeName,
        displayName,
        position,
        uptime,
        type,
        version,
        statusColor,
        statusColorRGB,
        statusText,
        factoryReset,
        lock,
        locate,
        eventSDIInput1NoInput,
        eventSDIInput2NoInput,
        eventSDIInput3NoInput,
        eventPSU1Failure,
        eventPSU2Failure,
        in1,
        in2,
        in3,
        reclock1,
        reclock2,
        reclock3,
        sourceOut1,
        sourceOut2,
        sourceOut3,
        eventPrimaryPowermissing,
        eventRedundantPowermissing,
        signalType,
        boardID,
        out1,
        out2,
        out3,
        eventVideoInput1NoInput,
        eventVideoInput3NoInput,
        eventVideoInput4NoInput,
        eventPrimaryPowermissingSNMP,
        eventRedundantPowermissingSNMP,
        eventVideoInput1NoInputSNMP,
        eventVideoInput3NoInputSNMP,
        eventVideoInput4NoInputSNMP,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
