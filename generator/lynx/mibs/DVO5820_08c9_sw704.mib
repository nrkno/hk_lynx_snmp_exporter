-- Machine generated MIB file, do not edit!
--
-- MIB file for DVO5820, type code 08.C9, software label 704
-- Generated on Tuesday, 09-Aug-16 14:34:16 UTC
-- CVS $Id: DVO5820_08c9_sw704.mib,v 1.3 2016/08/09 14:34:18 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

DVO5820-08c9-sw704-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

dvo5820-08c9-sw704 MODULE-IDENTITY
    LAST-UPDATED "201608091434Z"
    ORGANIZATION "LYNX Technik AG"
    CONTACT-INFO "LYNX Technik AG
        Brunnenweg 3
        64331 Weiterstadt
        http://www.lynx-technik.com
        mailto:support@lynx-technik.com"
    DESCRIPTION "MIB module definition for DVO5820, type code 08.C9, software label 704"
    REVISION "201608091434Z"
    DESCRIPTION "Generated by LYNX Asset Database"
    ::= { mib-modules 2249704 }

dvo5820-08c9 OBJECT-IDENTITY
    STATUS current
    DESCRIPTION "LYNX device type DVO5820"
    ::= { products 2249 }

sw704 OBJECT-IDENTITY
    STATUS current
    DESCRIPTION "Software label 704"
    ::= { dvo5820-08c9 704 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeSFPPinning1 ::= TEXTUAL-CONVENTION
    STATUS current
    DESCRIPTION "Enumeration"
    SYNTAX INTEGER {
        none(0),
        msa(1),
        gennum(2)
    }

TypeIn1 ::= TEXTUAL-CONVENTION
    STATUS current
    DESCRIPTION "Enumeration"
    SYNTAX INTEGER {
        missing(0),
        sDSDI(1),
        hDSDI(2),
        n3GSDI(3),
        hD3G(4),
        present(5)
    }

TypeSourceInput2 ::= TEXTUAL-CONVENTION
    STATUS current
    DESCRIPTION "Enumeration"
    SYNTAX INTEGER {
        electrical(0),
        optical(1)
    }

TypeEventSDIInput1NoInputSNMP ::= TEXTUAL-CONVENTION
    STATUS current
    DESCRIPTION "Enumeration"
    SYNTAX INTEGER {
        none(0),
        onOnly(1),
        offOnly(2),
        onOff(3)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

eventSDIInput1NoInput OBJECT-TYPE
    SYNTAX OnOffValue
    MAX-ACCESS read-only
    STATUS current
    DESCRIPTION "Info Event: SDI Input 1 No Input"
    ::= { paramEntry 14 }

eventSDIInput2NoInput OBJECT-TYPE
    SYNTAX OnOffValue
    MAX-ACCESS read-only
    STATUS current
    DESCRIPTION "Info Event: SDI Input 2 No Input"
    ::= { paramEntry 15 }

inputSignalQuality1Opt OBJECT-TYPE
    SYNTAX FixedPointValue1
    MAX-ACCESS read-only
    STATUS current
    DESCRIPTION "Input signal quality 1 (optical)"
    ::= { paramEntry 16 }

sFPModuleType1 OBJECT-TYPE
    SYNTAX DisplayString
    MAX-ACCESS read-only
    STATUS current
    DESCRIPTION "displays the type of detected SFP-Module 1. The SFP part number will also be  displayed if SFP-Module is unknown."
    ::= { paramEntry 17 }

sFPModulePartNumber1 OBJECT-TYPE
    SYNTAX DisplayString
    MAX-ACCESS read-only
    STATUS current
    DESCRIPTION "Displays the part number of used SFP Module"
    ::= { paramEntry 18 }

sFPPinning1 OBJECT-TYPE
    SYNTAX TypeSFPPinning1
    MAX-ACCESS read-only
    STATUS current
    DESCRIPTION "shows pinning of used SFP Module (gennum/msa)"
    ::= { paramEntry 19 }

inputSignalQuality2Opt OBJECT-TYPE
    SYNTAX FixedPointValue1
    MAX-ACCESS read-only
    STATUS current
    DESCRIPTION "Input signal quality 2 (optical)"
    ::= { paramEntry 20 }

sFPModuleType2 OBJECT-TYPE
    SYNTAX DisplayString
    MAX-ACCESS read-only
    STATUS current
    DESCRIPTION "displays the type of detected SFP-Module 2. The SFP part number will also be  displayed if SFP-Module is unknown."
    ::= { paramEntry 21 }

sFPModulePartNumber2 OBJECT-TYPE
    SYNTAX DisplayString
    MAX-ACCESS read-only
    STATUS current
    DESCRIPTION "Displays the part number of used SFP Module"
    ::= { paramEntry 22 }

sFPPinning2 OBJECT-TYPE
    SYNTAX TypeSFPPinning1
    MAX-ACCESS read-only
    STATUS current
    DESCRIPTION "shows pinning of used SFP Module (gennum/msa)"
    ::= { paramEntry 23 }

in1 OBJECT-TYPE
    SYNTAX TypeIn1
    MAX-ACCESS read-only
    STATUS current
    DESCRIPTION "Input status channel 1"
    ::= { paramEntry 24 }

in2 OBJECT-TYPE
    SYNTAX TypeIn1
    MAX-ACCESS read-only
    STATUS current
    DESCRIPTION "Input status channel 2"
    ::= { paramEntry 25 }

reclock1 OBJECT-TYPE
    SYNTAX OnOffValue
    MAX-ACCESS read-write
    STATUS current
    DESCRIPTION "select SDI reclocking on output 1"
    ::= { paramEntry 26 }

reclock2 OBJECT-TYPE
    SYNTAX OnOffValue
    MAX-ACCESS read-write
    STATUS current
    DESCRIPTION "select SDI reclocking on output 2"
    ::= { paramEntry 27 }

sourceInput2 OBJECT-TYPE
    SYNTAX TypeSourceInput2
    MAX-ACCESS read-write
    STATUS current
    DESCRIPTION "Select Source for Input 2 from electrical or optical connector"
    ::= { paramEntry 28 }

autoDisableOpticalOutput OBJECT-TYPE
    SYNTAX OnOffValue
    MAX-ACCESS read-write
    STATUS current
    DESCRIPTION "automatically disable (power down) the laser transmitter of the optical output if no valid input signal is connected."
    ::= { paramEntry 29 }

boardID OBJECT-TYPE
    SYNTAX Integer32
    MAX-ACCESS read-only
    STATUS current
    DESCRIPTION "BoardID"
    ::= { paramEntry 30 }

eventPrimaryPowermissing OBJECT-TYPE
    SYNTAX OnOffValue
    MAX-ACCESS read-only
    STATUS current
    DESCRIPTION "Info Event: Primary Power missing"
    ::= { paramEntry 31 }

eventRedundantPowermissing OBJECT-TYPE
    SYNTAX OnOffValue
    MAX-ACCESS read-only
    STATUS current
    DESCRIPTION "Info Event: Redundant Power missing"
    ::= { paramEntry 32 }

out1 OBJECT-TYPE
    SYNTAX TypeIn1
    MAX-ACCESS read-only
    STATUS current
    DESCRIPTION "Output status channel 1"
    ::= { paramEntry 33 }

out2 OBJECT-TYPE
    SYNTAX TypeIn1
    MAX-ACCESS read-only
    STATUS current
    DESCRIPTION "Output status channel 2"
    ::= { paramEntry 34 }

eventSDIInput1NoInputSNMP OBJECT-TYPE
    SYNTAX TypeEventSDIInput1NoInputSNMP
    MAX-ACCESS read-write
    STATUS current
    DESCRIPTION "SNMP Trap for  Event: SDI Input 1 No Input"
    ::= { paramEntry 35 }

eventSDIInput2NoInputSNMP OBJECT-TYPE
    SYNTAX TypeEventSDIInput1NoInputSNMP
    MAX-ACCESS read-write
    STATUS current
    DESCRIPTION "SNMP Trap for  Event: SDI Input 2 No Input"
    ::= { paramEntry 36 }

eventPrimaryPowermissingSNMP OBJECT-TYPE
    SYNTAX TypeEventSDIInput1NoInputSNMP
    MAX-ACCESS read-write
    STATUS current
    DESCRIPTION "SNMP Trap for  Event: Primary Power missing"
    ::= { paramEntry 37 }

eventRedundantPowermissingSNMP OBJECT-TYPE
    SYNTAX TypeEventSDIInput1NoInputSNMP
    MAX-ACCESS read-write
    STATUS current
    DESCRIPTION "SNMP Trap for  Event: Redundant Power missing"
    ::= { paramEntry 38 }

sFP1OutPower OBJECT-TYPE
    SYNTAX DisplayString
    MAX-ACCESS read-only
    STATUS current
    DESCRIPTION "displays the average output power of detected SFP-Module 1."
    ::= { paramEntry 39 }

sFP1Wavelength OBJECT-TYPE
    SYNTAX DisplayString
    MAX-ACCESS read-only
    STATUS current
    DESCRIPTION "displays the wavelength of detected SFP-Module 1."
    ::= { paramEntry 40 }

sFP2OutPower OBJECT-TYPE
    SYNTAX DisplayString
    MAX-ACCESS read-only
    STATUS current
    DESCRIPTION "displays the average output power of detected SFP-Module 2."
    ::= { paramEntry 41 }

sFP2Wavelength OBJECT-TYPE
    SYNTAX DisplayString
    MAX-ACCESS read-only
    STATUS current
    DESCRIPTION "displays the wavelength of detected SFP-Module 2."
    ::= { paramEntry 42 }

sNumber OBJECT-TYPE
    SYNTAX DisplayString
    MAX-ACCESS read-only
    STATUS current
    DESCRIPTION "Serial Number"
    ::= { paramEntry 43 }

-- Parameter table
paramTable OBJECT-TYPE
    SYNTAX SEQUENCE OF ParamEntry
    MAX-ACCESS not-accessible
    STATUS current
    DESCRIPTION "Table of DVO5820 parameters"
    ::= { sw704 1 }

paramEntry OBJECT-TYPE
    SYNTAX ParamEntry
    MAX-ACCESS not-accessible
    STATUS current
    DESCRIPTION "A row in the table of DVO5820 parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    eventSDIInput1NoInput OnOffValue,
    eventSDIInput2NoInput OnOffValue,
    inputSignalQuality1Opt FixedPointValue1,
    sFPModuleType1 DisplayString,
    sFPModulePartNumber1 DisplayString,
    sFPPinning1 TypeSFPPinning1,
    inputSignalQuality2Opt FixedPointValue1,
    sFPModuleType2 DisplayString,
    sFPModulePartNumber2 DisplayString,
    sFPPinning2 TypeSFPPinning1,
    in1 TypeIn1,
    in2 TypeIn1,
    reclock1 OnOffValue,
    reclock2 OnOffValue,
    sourceInput2 TypeSourceInput2,
    autoDisableOpticalOutput OnOffValue,
    boardID Integer32,
    eventPrimaryPowermissing OnOffValue,
    eventRedundantPowermissing OnOffValue,
    out1 TypeIn1,
    out2 TypeIn1,
    eventSDIInput1NoInputSNMP TypeEventSDIInput1NoInputSNMP,
    eventSDIInput2NoInputSNMP TypeEventSDIInput1NoInputSNMP,
    eventPrimaryPowermissingSNMP TypeEventSDIInput1NoInputSNMP,
    eventRedundantPowermissingSNMP TypeEventSDIInput1NoInputSNMP,
    sFP1OutPower DisplayString,
    sFP1Wavelength DisplayString,
    sFP2OutPower DisplayString,
    sFP2Wavelength DisplayString,
    sNumber DisplayString }

-- Conformance statements
conformance OBJECT-IDENTITY
    STATUS current
    DESCRIPTION "Conformance declaration of DVO5820"
    ::= { sw704 2 }

paramGroup OBJECT-GROUP
    OBJECTS {
        typeName,
        displayName,
        position,
        uptime,
        type,
        version,
        statusColor,
        statusColorRGB,
        statusText,
        factoryReset,
        lock,
        locate,
        eventSDIInput1NoInput,
        eventSDIInput2NoInput,
        inputSignalQuality1Opt,
        sFPModuleType1,
        sFPModulePartNumber1,
        sFPPinning1,
        inputSignalQuality2Opt,
        sFPModuleType2,
        sFPModulePartNumber2,
        sFPPinning2,
        in1,
        in2,
        reclock1,
        reclock2,
        sourceInput2,
        autoDisableOpticalOutput,
        boardID,
        eventPrimaryPowermissing,
        eventRedundantPowermissing,
        out1,
        out2,
        eventSDIInput1NoInputSNMP,
        eventSDIInput2NoInputSNMP,
        eventPrimaryPowermissingSNMP,
        eventRedundantPowermissingSNMP,
        sFP1OutPower,
        sFP1Wavelength,
        sFP2OutPower,
        sFP2Wavelength,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
