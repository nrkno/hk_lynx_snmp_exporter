-- Machine generated MIB file, do not edit!
--
-- MIB file for DVD5820, type code 08.C7, software label 704
-- Generated on Tuesday, 09-Aug-16 14:30:38 UTC
-- CVS $Id: DVD5820_08c7_sw704.mib,v 1.3 2016/08/09 14:30:40 jvo Exp $
--
-- Copyright 2003-2016 by LYNX Technik AG
--
-- These coded instructions, statements, and computer programs  contain
-- unpublished proprietary information  written  by LYNX Technik AG and
-- are protected by Federal copyright law. They  may  not  be disclosed
-- to  third  parties  or copied or duplicated in any form, in whole or
-- in part, without the prior written consent of LYNX Technik AG.
--

DVD5820-08c7-sw704-MIB DEFINITIONS ::= BEGIN
IMPORTS
    MODULE-IDENTITY, OBJECT-IDENTITY, OBJECT-TYPE,
    Integer32, TimeTicks FROM SNMPv2-SMI -- RFC2578
    TEXTUAL-CONVENTION, DisplayString FROM SNMPv2-TC -- RFC2579
    MODULE-COMPLIANCE, OBJECT-GROUP FROM SNMPv2-CONF -- RFC2580
    mib-modules, products,
    FixedPointValue1, FixedPointValue2, FixedPointValue3, OnOffValue FROM LYNX-SMI;

dvd5820-08c7-sw704 MODULE-IDENTITY
    LAST-UPDATED "201608091430Z"
    ORGANIZATION "LYNX Technik AG"
    CONTACT-INFO "LYNX Technik AG
        Brunnenweg 3
        64331 Weiterstadt
        http://www.lynx-technik.com
        mailto:support@lynx-technik.com"
    DESCRIPTION "MIB module definition for DVD5820, type code 08.C7, software label 704"
    REVISION "201608091430Z"
    DESCRIPTION "Generated by LYNX Asset Database"
    ::= { mib-modules 2247704 }

dvd5820-08c7 OBJECT-IDENTITY
    STATUS current
    DESCRIPTION "LYNX device type DVD5820"
    ::= { products 2247 }

sw704 OBJECT-IDENTITY
    STATUS current
    DESCRIPTION "Software label 704"
    ::= { dvd5820-08c7 704 }

-- Type definitions
TypeStatusColor ::= TEXTUAL-CONVENTION
    STATUS current
    DESCRIPTION "Enumeration"
    SYNTAX INTEGER {
        unknown(0),
        black(1),
        green(2),
        yellow(3),
        red(4)
    }

TypeFactoryReset ::= TEXTUAL-CONVENTION
    STATUS current
    DESCRIPTION "Enumeration"
    SYNTAX INTEGER {
        press(0)
    }

TypeIn1 ::= TEXTUAL-CONVENTION
    STATUS current
    DESCRIPTION "Enumeration"
    SYNTAX INTEGER {
        missing(0),
        sDSDI(1),
        hDSDI(2),
        n3GSDI(3),
        hD3G(4),
        present(5)
    }

TypeSourceOut1 ::= TEXTUAL-CONVENTION
    STATUS current
    DESCRIPTION "Enumeration"
    SYNTAX INTEGER {
        in1(0),
        in2(1)
    }

TypeEventSDIInput1NoInputSNMP ::= TEXTUAL-CONVENTION
    STATUS current
    DESCRIPTION "Enumeration"
    SYNTAX INTEGER {
        none(0),
        onOnly(1),
        offOnly(2),
        onOff(3)
    }

-- Parameter definitions
typeName OBJECT-TYPE
    SYNTAX DisplayString
    MAX-ACCESS read-only
    STATUS current
    DESCRIPTION "LYNX product type name"
    ::= { paramEntry 1 }

displayName OBJECT-TYPE
    SYNTAX DisplayString
    MAX-ACCESS read-write
    STATUS current
    DESCRIPTION "Name of device (potentially user-defined), as stored in device-controller"
    ::= { paramEntry 2 }

position OBJECT-TYPE
    SYNTAX OCTET STRING (SIZE (0..63))
    MAX-ACCESS read-only
    STATUS current
    DESCRIPTION "Full-qualified position information (e.g. as used in address-field of remoteIF protocol)"
    ::= { paramEntry 3 }

uptime OBJECT-TYPE
    SYNTAX TimeTicks
    MAX-ACCESS read-only
    STATUS current
    DESCRIPTION "Connection time of the device to this UI (in seconds)"
    ::= { paramEntry 4 }

type OBJECT-TYPE
    SYNTAX DisplayString
    MAX-ACCESS read-only
    STATUS current
    DESCRIPTION "Device type code"
    ::= { paramEntry 5 }

version OBJECT-TYPE
    SYNTAX DisplayString
    MAX-ACCESS read-only
    STATUS current
    DESCRIPTION "Device version information"
    ::= { paramEntry 6 }

statusColor OBJECT-TYPE
    SYNTAX TypeStatusColor
    MAX-ACCESS read-only
    STATUS current
    DESCRIPTION "The current color of the Devices Master LED (red/green/yellow)"
    ::= { paramEntry 7 }

statusColorRGB OBJECT-TYPE
    SYNTAX DisplayString
    MAX-ACCESS read-only
    STATUS current
    DESCRIPTION "The current color of the Devices Master LED as #RRGGBB"
    ::= { paramEntry 8 }

statusText OBJECT-TYPE
    SYNTAX DisplayString
    MAX-ACCESS read-only
    STATUS current
    DESCRIPTION "The current status text (OK or error-details)"
    ::= { paramEntry 9 }

factoryReset OBJECT-TYPE
    SYNTAX TypeFactoryReset
    MAX-ACCESS read-write
    STATUS current
    DESCRIPTION "Reset device to factory default values (set value to PRESS for execution)"
    ::= { paramEntry 10 }

lock OBJECT-TYPE
    SYNTAX OnOffValue
    MAX-ACCESS read-write
    STATUS current
    DESCRIPTION "Lock Device"
    ::= { paramEntry 11 }

locate OBJECT-TYPE
    SYNTAX OnOffValue
    MAX-ACCESS read-write
    STATUS current
    DESCRIPTION "toggle the locating function (yellow flashing master LED) ON/OFF"
    ::= { paramEntry 12 }

eventSDIInput1NoInput OBJECT-TYPE
    SYNTAX OnOffValue
    MAX-ACCESS read-only
    STATUS current
    DESCRIPTION "Info Event: SDI Input 1 No Input"
    ::= { paramEntry 14 }

eventSDIInput2NoInput OBJECT-TYPE
    SYNTAX OnOffValue
    MAX-ACCESS read-only
    STATUS current
    DESCRIPTION "Info Event: SDI Input 2 No Input"
    ::= { paramEntry 15 }

in1 OBJECT-TYPE
    SYNTAX TypeIn1
    MAX-ACCESS read-only
    STATUS current
    DESCRIPTION "Input status channel 1"
    ::= { paramEntry 16 }

in2 OBJECT-TYPE
    SYNTAX TypeIn1
    MAX-ACCESS read-only
    STATUS current
    DESCRIPTION "Input status channel 2"
    ::= { paramEntry 17 }

reclock1 OBJECT-TYPE
    SYNTAX OnOffValue
    MAX-ACCESS read-write
    STATUS current
    DESCRIPTION "select SDI reclocking on input 1"
    ::= { paramEntry 18 }

reclock2 OBJECT-TYPE
    SYNTAX OnOffValue
    MAX-ACCESS read-write
    STATUS current
    DESCRIPTION "select SDI reclocking on input 2"
    ::= { paramEntry 19 }

sourceOut1 OBJECT-TYPE
    SYNTAX TypeSourceOut1
    MAX-ACCESS read-write
    STATUS current
    DESCRIPTION "Select Source stream for output 1 from input 1 or 2"
    ::= { paramEntry 20 }

sourceOut2 OBJECT-TYPE
    SYNTAX TypeSourceOut1
    MAX-ACCESS read-write
    STATUS current
    DESCRIPTION "Select Source stream for output 2 from input 1 or 2"
    ::= { paramEntry 21 }

boardID OBJECT-TYPE
    SYNTAX Integer32
    MAX-ACCESS read-only
    STATUS current
    DESCRIPTION "BoardID"
    ::= { paramEntry 22 }

eventPrimaryPowermissing OBJECT-TYPE
    SYNTAX OnOffValue
    MAX-ACCESS read-only
    STATUS current
    DESCRIPTION "Info Event: Primary Power missing"
    ::= { paramEntry 23 }

eventRedundantPowermissing OBJECT-TYPE
    SYNTAX OnOffValue
    MAX-ACCESS read-only
    STATUS current
    DESCRIPTION "Info Event: Redundant Power missing"
    ::= { paramEntry 24 }

out1 OBJECT-TYPE
    SYNTAX TypeIn1
    MAX-ACCESS read-only
    STATUS current
    DESCRIPTION "Output status channel 1"
    ::= { paramEntry 25 }

out2 OBJECT-TYPE
    SYNTAX TypeIn1
    MAX-ACCESS read-only
    STATUS current
    DESCRIPTION "Output status channel 2"
    ::= { paramEntry 26 }

eventSDIInput1NoInputSNMP OBJECT-TYPE
    SYNTAX TypeEventSDIInput1NoInputSNMP
    MAX-ACCESS read-write
    STATUS current
    DESCRIPTION "SNMP Trap for  Event: SDI Input 1 No Input"
    ::= { paramEntry 27 }

eventSDIInput2NoInputSNMP OBJECT-TYPE
    SYNTAX TypeEventSDIInput1NoInputSNMP
    MAX-ACCESS read-write
    STATUS current
    DESCRIPTION "SNMP Trap for  Event: SDI Input 2 No Input"
    ::= { paramEntry 28 }

eventPrimaryPowermissingSNMP OBJECT-TYPE
    SYNTAX TypeEventSDIInput1NoInputSNMP
    MAX-ACCESS read-write
    STATUS current
    DESCRIPTION "SNMP Trap for  Event: Primary Power missing"
    ::= { paramEntry 29 }

eventRedundantPowermissingSNMP OBJECT-TYPE
    SYNTAX TypeEventSDIInput1NoInputSNMP
    MAX-ACCESS read-write
    STATUS current
    DESCRIPTION "SNMP Trap for  Event: Redundant Power missing"
    ::= { paramEntry 30 }

sNumber OBJECT-TYPE
    SYNTAX DisplayString
    MAX-ACCESS read-only
    STATUS current
    DESCRIPTION "Serial Number"
    ::= { paramEntry 31 }

-- Parameter table
paramTable OBJECT-TYPE
    SYNTAX SEQUENCE OF ParamEntry
    MAX-ACCESS not-accessible
    STATUS current
    DESCRIPTION "Table of DVD5820 parameters"
    ::= { sw704 1 }

paramEntry OBJECT-TYPE
    SYNTAX ParamEntry
    MAX-ACCESS not-accessible
    STATUS current
    DESCRIPTION "A row in the table of DVD5820 parameters"
    INDEX { IMPLIED position }
    ::= { paramTable 1 }

ParamEntry ::= SEQUENCE {
    typeName DisplayString,
    displayName DisplayString,
    position OCTET STRING,
    uptime TimeTicks,
    type DisplayString,
    version DisplayString,
    statusColor TypeStatusColor,
    statusColorRGB DisplayString,
    statusText DisplayString,
    factoryReset TypeFactoryReset,
    lock OnOffValue,
    locate OnOffValue,
    eventSDIInput1NoInput OnOffValue,
    eventSDIInput2NoInput OnOffValue,
    in1 TypeIn1,
    in2 TypeIn1,
    reclock1 OnOffValue,
    reclock2 OnOffValue,
    sourceOut1 TypeSourceOut1,
    sourceOut2 TypeSourceOut1,
    boardID Integer32,
    eventPrimaryPowermissing OnOffValue,
    eventRedundantPowermissing OnOffValue,
    out1 TypeIn1,
    out2 TypeIn1,
    eventSDIInput1NoInputSNMP TypeEventSDIInput1NoInputSNMP,
    eventSDIInput2NoInputSNMP TypeEventSDIInput1NoInputSNMP,
    eventPrimaryPowermissingSNMP TypeEventSDIInput1NoInputSNMP,
    eventRedundantPowermissingSNMP TypeEventSDIInput1NoInputSNMP,
    sNumber DisplayString }

-- Conformance statements
conformance OBJECT-IDENTITY
    STATUS current
    DESCRIPTION "Conformance declaration of DVD5820"
    ::= { sw704 2 }

paramGroup OBJECT-GROUP
    OBJECTS {
        typeName,
        displayName,
        position,
        uptime,
        type,
        version,
        statusColor,
        statusColorRGB,
        statusText,
        factoryReset,
        lock,
        locate,
        eventSDIInput1NoInput,
        eventSDIInput2NoInput,
        in1,
        in2,
        reclock1,
        reclock2,
        sourceOut1,
        sourceOut2,
        boardID,
        eventPrimaryPowermissing,
        eventRedundantPowermissing,
        out1,
        out2,
        eventSDIInput1NoInputSNMP,
        eventSDIInput2NoInputSNMP,
        eventPrimaryPowermissingSNMP,
        eventRedundantPowermissingSNMP,
        sNumber }
    STATUS current
    DESCRIPTION "Conformance group containing all device parameters"
    ::= { conformance 1 }

paramCompliance MODULE-COMPLIANCE
    STATUS current
    DESCRIPTION "Compliance specification"
    MODULE -- This module
    MANDATORY-GROUPS { paramGroup }
    ::= { conformance 2 }

END
